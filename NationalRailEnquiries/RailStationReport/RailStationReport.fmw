FME workspace RailStationReport.fmw

Parameters:
- RailwayStation = SOU
- DestDataset_MSWORD = output   # Destination Microsoft Word file
- SourceDataset_XML = /Users/fme/Desktop/FMEWT 2018/Sweco/2 - Web Data & Reporting Workflows/Web Data and Reporting/HTMLReport/CNM_ArrDepDetails_CancelledTrain.xml   # Source XML File(s)
- SourceDataset_ESRISHAPE = /Users/fme/Desktop/FMEWT 2018/Sweco/2 - Web Data & Reporting Workflows/Web Data and Reporting/HTMLReport/TestCorrectNetwork.shp   # Source Esri Shapefile(s)
- SourceDataset_ESRISHAPE_3 = /Users/fme/Desktop/FMEWT 2018/Sweco/2 - Web Data & Reporting Workflows/Web Data and Reporting/HTMLReport/RailwayStations.shp   # Source Esri Shapefile(s)
- DestDataset_HTML_3 = default   # HTML Files(*.html)|*.html Destination Html File
- DestDataset_HTML = test2   # HTML Files(*.html)|*.html Destination Html File

Readers:
- XML_1: XML from $(SourceDataset_XML)
- ESRISHAPE_1: ESRISHAPE from $(SourceDataset_ESRISHAPE_3)
- ESRISHAPE_2: ESRISHAPE from $(SourceDataset_ESRISHAPE)

Writers:
- HTML_1: HTML to $(DestDataset_HTML)
- HTML_2: HTML to $(DestDataset_HTML_3)
- MSWORD_1: MSWORD to $(DestDataset_MSWORD)

Note: RailwayStations: / All of the GB Stations with geometry
RailwayStations (reader ESRISHAPE_1)
    attributes: stationNam char(254), CRS_Code char(254), XCOORD char(200), YCOORD char(200)
    -> Tester_Requested_Station
Tester_Requested_Station
    BOOL_OP = OR
    TEST_CLAUSE = TEST @Value(CRS_Code) = $(RailwayStation)
    PASSED -> VariableSetter_X
    FAILED -> FeatureMerger_subsequent [SUPPLIER]
    FAILED -> FeatureMerger_previous [SUPPLIER]
Note: Merge lines together based on ServiceID
LineCombiner
    ACCUM_ATTRS_NAME = Merge Incoming Attributes
    BREAK = no
    BREAK_CONNECTION_ACROSS_SETS = Yes
    CONNECT_Z_MODE = First Wins
    CONSIDER_NODE_ELEVATION = no
    DEAGGREGATE_GEOMETRY = Deaggregate
    DIRECTION_NAME = direction
    GROUP_BY = serviceID
    LINES_AS_SEGMENTS = No
    PRESERVE = no
    TOPOLOGY = End noded
    LINE -> ShortestPathFinder [FROM-TO]
TestCorrectNetwork (reader ESRISHAPE_2)
    attributes: FEATCODE long, LEGEND char(42)
    -> ShortestPathFinder [NETWORK]
ShortestPathFinder
    ALLOW_UTURNS = Yes
    REORDER_CHOICE = None
    SNAP_POINTS = Yes
    SNAP_TOLERANCE = 5000
    WEIGHT_ATTR_CHOICE = By Length
    PATH -> VariableRetriever_5
MSWordStyler
    ITEM_TYPE = Heading
RailwayStations (writer MSWORD_1)
    attributes: stationNam text, CRS_Code text, XCOORD text, YCOORD text

Bookmark: SOAP API Call to National Rail Data Feed
Note: This uses the LDB Webservice (PV). Details available here: http://www.nationalrail.co.uk/100296.aspx
Creator_2
    GEOMTYPE = Geometry Object
    NUM = 1
    CREATED -> HTTPCaller_2
HTTPCaller_2
    CONNECTION_TIMEOUT_LENGTH = 60
    ERROR_ATTR = _error
    FOLLOW_REDIRECTS = Yes
    HTTP_METHOD = POST
    SAVE_FILE = Attribute
    STATUS_CODE_ATTR = _http_status_code
    TARGET_ATTR = _response_body
    TARGET_ATTR_ENCODING = auto-detect
    TARGET_URL = https://lite.realtime.nationalrail.co.uk/OpenLDBWS/ldb11.asmx
    TRANSFER_TIMEOUT_LENGTH = 90
    UPLOAD_BODY:
      <soap:Envelope xmlns:soap="http://www.w3.org/2003/05/soap-envelope" xmlns:typ="http://thalesgroup.com/RTTI/2013-11-28/Token/types" xmlns:ldb="http://thalesgroup.com/RTTI/2017-10-01/ldb/">
         <soap:Header>
            <typ:AccessToken>
               <typ:TokenValue>26b2c883-e22f-401e-b1fd-be2deb7539f2</typ:TokenValue>
            </typ:AccessToken>
         </soap:Header>
         <soap:Body>
            <ldb:GetArrDepBoardWithDetailsRequest>
               <ldb:numRows>20</ldb:numRows>
               <ldb:crs>$(RailwayStation)</ldb:crs>
               <ldb:timeWindow>120</ldb:timeWindow>
            </ldb:GetArrDepBoardWithDetailsRequest>
         </soap:Body>
      </soap:Envelope>
    UPLOAD_CONTENT_TYPE = SOAP XML (application/soap+xml)
    UPLOAD_TYPE = Specify Upload Body
    USE_COOKIES = No
    VERIFY_SSL_CERTIFICATES = Yes
    -> XMLFragmenter_2
XMLFragmenter_2
    ATTRIBUTE_XML = _response_body
    EMBEDDED_EXPRESSIONS = lt7:service
    FEATURE_TYPES_FORMAT_NAME = XML
    FLATTEN_OPTIONS = <structure separator="." map-empty-elements="yes" matched-prefix="attributes" matched-attributes="yes" cardinality="+{?}" structure-prefix="" child-position-attribute="" except-expression="" ui-mode="basic" matched-ancestor-attributes=""/>
    MERGE_ATTRS = No
    NEW_ATTRIBUTES = origin.location.crs origin.location.locationName destination.location.crs destination.location.locationName sta eta std etd delayReason platform operator subsequentCallingPoints serviceType serviceID
    XML_SOURCE_TYPE = Attribute with XML document
    FRAGMENTS -> ListExploder_Subsequent
    FRAGMENTS -> ListExploder_Previous

Bookmark: Requested Station coords
VariableSetter_X
    SCOPE = Global
    VALUE = @Value(XCOORD)
    VARNAME = X
    -> VariableSetter_Y
VariableSetter_Y
    SCOPE = Global
    VALUE = @Value(YCOORD)
    VARNAME = Y
    -> VariableSetter_Y_2
VariableSetter_Y_2
    SCOPE = Global
    VALUE = @Value(stationNam)
    VARNAME = stationName

Bookmark: Cheltenham Spa (offlne)
service (reader XML_1) [off]
    attributes: cancelReason xml_char(63), delayReason xml_char(58), destination.location.crs xml_char(4), destination.location.locationName xml_char(22), destination.location.via xml_char(19), eta xml_char(8), etd xml_char(8), length xml_decimal(2,0), operator xml_char(22), operatorCode xml_char(3), origin.location.crs xml_char(4), origin.location.locationName xml_char(22), previousCallingPoints.callingPointList.callingPoint{}.at xml_char(10), previousCallingPoints.callingPointList.callingPoint{}.crs xml_char(4), previousCallingPoints.callingPointList.callingPoint{}.et xml_char(8), previousCallingPoints.callingPointList.callingPoint{}.length xml_decimal(2,0), previousCallingPoints.callingPointList.callingPoint{}.locationName xml_char(23), previousCallingPoints.callingPointList.callingPoint{}.st xml_char(6), rsid xml_char(9), serviceID xml_char(25), serviceType xml_char(6), sta xml_char(6), std xml_char(6), subsequentCallingPoints.callingPointList.callingPoint{}.crs xml_char(4), subsequentCallingPoints.callingPointList.callingPoint{}.et xml_char(8), subsequentCallingPoints.callingPointList.callingPoint{}.length xml_decimal(2,0), subsequentCallingPoints.callingPointList.callingPoint{}.locationName xml_char(25), subsequentCallingPoints.callingPointList.callingPoint{}.st xml_char(6), xml_fragment xml_xml, xml_id xml_char(24),
      xml_matched_element xml_char(8), xml_parent_child_pos xml_char(1), xml_parent_id xml_char(1)
    -> ListExploder_Previous
    -> ListExploder_Subsequent

Bookmark: Subsequent Calling Points
Note: Turn each list element (subsequent stop) into it's own feature
ListExploder_Subsequent
    ATTR_ACCUM_MODE = Merge List Attributes
    ATTR_CONFLICT_RES = Use List Attribute Values
    INDEX_ATTR = _element_index
    LIST_ATTR = subsequentCallingPoints.callingPointList.callingPoint{}
    ELEMENTS -> FeatureMerger_subsequent [REQUESTOR]
Note: Get the geometry for subsequent stations
FeatureMerger_subsequent
    ATTR_ACCUM_MODE = Merge Supplier
    ATTR_CONFLICT_RES = Use Requestor
    IGNORE_NULLS = No
    JOIN_KEYS = @Value(crs) @Value(CRS_Code) AUTO
    MERGE_TYPE = Attributes and Geometry
    PROCESS_DUPS = NO
    REJECT_NULL_MISSING_KEYS = No
    SUPPLIERS_FIRST = No
    MERGED -> Sorter_3
Note: Ensure points enter the line builder in element order for each service id
Sorter_3
    SORT_PARM = serviceID ALPHA ASCENDING _element_index NUMERIC DESCENDING
    SORTED -> LineBuilder_2
Note: subsequent. List Element 0 is the next station. Biggest element number is the destination station
LineBuilder_2
    ACCUM_INPUT_ATTRS = Merge Incoming Attributes
    BREAKATTR = serviceID
    LINE -> VariableRetriever_3

Bookmark: Add the requested station coords to the line
VariableRetriever_3
    SCOPE = Global
    VALUE_ATTR = _X
    VARNAME = X
    -> VariableRetriever_4
VariableRetriever_4
    SCOPE = Global
    VALUE_ATTR = _Y
    VARNAME = Y
    -> VertexCreator_2
VertexCreator_2
    MODE_NAME = Add Point
    XVAL = @Value(_X)
    YVAL = @Value(_Y)
    -> LineCombiner

Bookmark: Previous Calling Points
Note: previous. List Element 0 is the origin station. Biggest element number is the station before the requested station
Note: Turn each list element (previous stop) into it's own feature
ListExploder_Previous
    ATTR_ACCUM_MODE = Merge List Attributes
    ATTR_CONFLICT_RES = Use List Attribute Values
    INDEX_ATTR = _element_index
    LIST_ATTR = previousCallingPoints.callingPointList.callingPoint{}
    ELEMENTS -> FeatureMerger_previous [REQUESTOR]
Note: Get the geometry for previous stations
FeatureMerger_previous
    ATTR_ACCUM_MODE = Merge Supplier
    ATTR_CONFLICT_RES = Use Requestor
    IGNORE_NULLS = No
    JOIN_KEYS = @Value(crs) @Value(CRS_Code) AUTO
    MERGE_TYPE = Attributes and Geometry
    PROCESS_DUPS = NO
    REJECT_NULL_MISSING_KEYS = No
    SUPPLIERS_FIRST = No
    MERGED -> Sorter
Note: Ensure points enter the line builder in element order for each service id
Sorter
    SORT_PARM = serviceID ALPHA ASCENDING _element_index NUMERIC ASCENDING
    SORTED -> LineBuilder
LineBuilder
    ACCUM_INPUT_ATTRS = Merge Incoming Attributes
    BREAKATTR = serviceID
    LINE -> VariableRetriever

Bookmark: Add the requested station coords to the line
VariableRetriever
    SCOPE = Global
    VALUE_ATTR = _X
    VARNAME = X
    -> VariableRetriever_2
VariableRetriever_2
    SCOPE = Global
    VALUE_ATTR = _Y
    VARNAME = Y
    -> VertexCreator
VertexCreator
    MODE_NAME = Add Point
    XVAL = @Value(_X)
    YVAL = @Value(_Y)
    -> LineCombiner

Bookmark: HTML Report
VariableRetriever_5
    SCOPE = Global
    VALUE_ATTR = stationName
    VARNAME = stationName
    -> AttributeManager
Note: Create popup text
AttributeManager
    ATTR_TABLE:
      SET_TO Route = FME_CONDITIONAL:DEFAULT_VALUE'@Value(origin.location.locationName) to @Value(destination.location.locationName)
        Scheduled Arrival:@Value(sta)
        Estimated Arrival: @Value(eta)'BOOL_OP;OR;COMPOSITE_TEST;<Unused>;TEST delayReason ATTRIBUTE_HAS_A_VALUE _FME_BLANK_STRING_;TEST etd ATTRIBUTE_HAS_A_VALUE _FME_BLANK_STRING_'@Value(origin.location.locationName) to @Value(destination.location.locationName)
        Scheduled Departure:@Value(std)
        Estimated Departure: @Value(etd)
        Delay Reason: @Value(delayReason)'BOOL_OP;OR;COMPOSITE_TEST;<Unused>;TEST delayReason ATTRIBUTE_HAS_A_VALUE _FME_BLANK_STRING_;TEST eta ATTRIBUTE_HAS_A_VALUE _FME_BLANK_STRING_'@Value(origin.location.locationName) to @Value(destination.location.locationName)
        Scheduled Departure:@Value(sta)
        Estimated Departure: @Value(eta)
        Delay Reason: @Value(delayReason)'BOOL_OP;OR;COMPOSITE_TEST;<Unused>;CASE_INSENSITIVE_TEST cancelReason ATTRIBUTE_HAS_A_VALUE _FME_BLANK_STRING_;TEST std ATTRIBUTE_HAS_A_VALUE _FME_BLANK_STRING_'@Value(origin.location.locationName) to @Value(destination.location.locationName)
        Scheduled Departure: @Value(std)
        @Value(cancelReason)

        'BOOL_OP;OR;COMPOSITE_TEST;<Unused>;CASE_INSENSITIVE_TEST cancelReason ATTRIBUTE_HAS_A_VALUE _FME_BLANK_STRING_;TEST sta ATTRIBUTE_HAS_A_VALUE _FME_BLANK_STRING_'@Value(origin.location.locationName) to @Value(destination.location.locationName)
        Scheduled Arrival: @Value(sta)
        @Value(cancelReason)'BOOL_OP;OR;COMPOSITE_TEST;<Unused>;TEST etd ATTRIBUTE_HAS_A_VALUE _FME_BLANK_STRING_'@Value(origin.location.locationName) to @Value(destination.location.locationName)
        Scheduled Departure:@Value(std)
        Estimated Departure: @Value(etd)'BOOL_OP;OR;COMPOSITE_TEST;<Unused>;TEST eta ATTRIBUTE_HAS_A_VALUE _FME_BLANK_STRING_'@Value(origin.location.locationName) to @Value(destination.location.locationName)
        Scheduled Arrival:@Value(std)
        Estimated Arrival: @Value(etd)'FME_NUM_CONDITIONS7___
    -> HTMLReportGenerator
HTMLReportGenerator
    CONTENT_LIST = HEADER MAP_GOOGLE TABLE HEADER HTML
    PAGE_CONFIG = HEADER{{TEXT;All Arrivals and Departures for @Value(stationName);HEADER;H1;ALIGNMENT;CENTER;COLOR;0,0,0;FME_CONTROLLER_QUERY_FILE;transformers/dependencies/html5/Header.fme}}MAP_GOOGLE{{LABEL;Route;COLOR;0,0,255;TOKEN;AIzaSyD4Tp9TcGs1omC0zXkut3r3i-xUxH_z0RY;FME_CONTROLLER_QUERY_FILE;transformers/dependencies/html5/Map (Google).fme}}TABLE{{STYLE;DEFAULT;TABLE;origin.location.locationName|Origin/destination.location.locationName|Destination/platform|Platform/sta|Scheduled Arrival/eta|Estimated Arrival/std|Scheduled Departure/etd|Estimated Departue/operator|Operator;FME_CONTROLLER_QUERY_FILE;transformers/dependencies/html5/Table.fme}}HEADER{{TEXT;Contains OS data © Crown copyright and database right (2018);HEADER;H6;ALIGNMENT;LEFT;COLOR;0,0,0;FME_CONTROLLER_QUERY_FILE;transformers/dependencies/html5/Header.fme}}HTML{{HTML;<img src="https://woking-shopping.co.uk/assets/img/NRE_Powered_logo.png" alt="Powered by National Rail Enquiries" style="width:400px">;FME_CONTROLLER_QUERY_FILE;transformers/dependencies/html5/Custom HTML.fme}}
    TITLE = @Value(stationName)
    -> StringReplacer
    -> HTML (writer HTML_2)
Note: HTML: default [HTML]
HTML (writer HTML_2)
    attributes: html_content buffer
StringReplacer
    CASE = NO
    FIND_TEXT = map.data.setStyle({fillColor: "rgb(0,0,255)", strokeColor: "rgb(0,0,255)"});
    NO_MATCH = _FME_NO_OP_
    REGEXP = NO
    REPLACE_TEXT:
      map.data.setStyle(function(feature) {
                          var line = feature.getProperty('name');
                          var color = line.includes("On time") ? 'MediumSeaGreen' : 'OrangeRed';
                          var weight = line.includes("On time") ? '2.5' : '5';
                          return {
                            strokeColor: color,
                            strokeWeight: weight,
                            strokeOpacity: 1
                          };
                      });
    SRC_ATTRS = html_content
    -> HTML (writer HTML_1)
Note: HTML: test2 [HTML]
HTML (writer HTML_1)
    attributes: html_content buffer
