FME workspace GraffitiDemo-2018.fmw
Title: GraffitiDemo-2018

Parameters:
- DestDataset_XLSXW = /Users/bpont/Documents   # Destination Microsoft Excel File

Readers:
- ARCGISONLINEFEATURES_1: ARCGISONLINEFEATURES

Writers:
- XLSXW_1: XLSXW to $(DestDataset_XLSXW)

Bookmark: Add ArcGIS Feature Service
Vancouver_Graffiti_Report (reader ARCGISONLINEFEATURES_1)
    attributes: OBJECTID esriFieldTypeOID, Date_ esriFieldTypeDate, ReporterName esriFieldTypeString(30), ReporterPhone esriFieldTypeString(20), ReporterEmail esriFieldTypeString(50), Description esriFieldTypeString(255), Location esriFieldTypeString(30), MaterialsUsed esriFieldTypeString(100), Resolved esriFieldTypeString(10), GlobalID esriFieldTypeGlobalID(38)
    -> DateTimeConverter

Bookmark: Snapshot of the Data
Note: For network issues you can use this:
Player [off]
    FEAT_TYPE_ATTR = fme_feature_type
    RECFILE = /tmp/wb_template_1524483263189_3711/1/Downloads/copyGraffiti.ffs
    PLAYED_BACK -> DateTimeConverter

Bookmark: Filter Resolved Issues and Format our Date
Note: Remove Time
DateTimeConverter
    DATETIME_ATTR = Date_
    OUT_FORMAT = %Y%m%d
    REPAIR_INPUT = NO
    -> Tester
Note: Test for 'Resolved' = 'Yes'
Tester
    BOOL_OP = AND
    TEST_CLAUSE:
      TEST arcgisonline_attachment{0}.id NOT_ATTRIBUTE_IS_MISSING ""
      TEST @Value(Resolved) NOT_= yes
    PASSED -> RasterReplacer
    PASSED -> AttributeKeeper_2
    PASSED -> Reprojector

Bookmark: Graffiti Attachement Image
Note: Create our Image from Binary
RasterReplacer
    BLOB_ATTR = arcgisonline_attachment{0}.data
    FORMAT = JPEG
    REMOVE_ATTRIBUTE = No
    -> AttributeManager
Note: Set Size and Position
AttributeManager
    ATTR_TABLE:
      SET_TO xlsx_col_id = 5
      SET_TO xlsx_row_id = 4
      SET_TO xlsx_raster_height = 160
      SET_TO xlsx_raster_width = 200
    -> AttributeKeeper
AttributeKeeper
    KEEP_ATTRS = Date_,xlsx_col_id,xlsx_raster_height,xlsx_row_id,xlsx_raster_width
    -> Work Order (writer XLSXW_1)

Bookmark: Create the Coordinates
Reprojector
    DEST = LL84
    INTERPOLATION_TYPE_NAME = Nearest Neighbor
    RASTER_CELL_SIZE = Preserve Cells
    RASTER_TOLERANCE = 0.0
    SOURCE = Read from feature
    REPROJECTED -> CoordinateExtractor
CoordinateExtractor
    IND = 0
    LIST_NAME = _indices
    MODE = All Coordinates
    X_ATTR = _x
    Y_ATTR = _y
    Z_ATTR = _z
    -> HTTPCaller

Bookmark: Location Map
Note: Call the Google Maps API to get a map as an attribute
HTTPCaller
    CONNECTION_TIMEOUT_LENGTH = 60
    ERROR_ATTR = _error
    FOLLOW_REDIRECTS = Yes
    HTTP_METHOD = GET
    RESPONSE_HEADER_LIST_ATTR = _headers
    SAVE_FILE = Attribute
    STATUS_CODE_ATTR = _http_status_code
    TARGET_ATTR = _response_body
    TARGET_ATTR_ENCODING = auto-detect
    TARGET_URL = http://maps.googleapis.com/maps/api/staticmap?size=200x200&&sensor=false&markers=color:red|size:mid|label:F|@Value(_indices{0}.y),@Value(_indices{0}.x)
    TRANSFER_TIMEOUT_LENGTH = 90
    USE_COOKIES = No
    VERIFY_SSL_CERTIFICATES = Yes
    -> RasterReplacer_2

Bookmark: Create Image and Set Position
RasterReplacer_2
    BLOB_ATTR = _response_body
    FORMAT = PNGRASTER
    REMOVE_ATTRIBUTE = No
    -> AttributeManager_2
AttributeManager_2
    ATTR_TABLE:
      SET_TO xlsx_col_id = 5
      SET_TO xlsx_row_id = 12
    -> Work Order (writer XLSXW_1)

Bookmark: Attribute Data
AttributeKeeper_2
    KEEP_ATTRS = MaterialsUsed,Date_,Description,ReporterName,ReporterPhone,Location,ReporterEmail
    -> AttributeExploder
Note: Creat 1 feature for each attribute
AttributeExploder
    ATTR_NAME_LABEL = _attr_name
    ATTR_VALUE_LABEL = _attr_value
    EXPLODING_TYPE = Features
    KEEP_ATTRIBUTES = Yes
    KEEP_GEOMETRY = No
    -> Tester_2
Note: remove date and fme_ attributes as features
Tester_2
    BOOL_OP = AND
    TEST_CLAUSE:
      TEST @Value(_attr_name) NOT_CONTAINS fme
      TEST @Value(_attr_name) NOT_CONTAINS date
    PASSED -> AttributeManager_3
Note: Set Col and Row Position for each feature. Note column renamed to 'C'
AttributeManager_3
    ATTR_TABLE:
      SET_TO xlsx_row_id = FME_CONDITIONAL:DEFAULT_VALUE'_FME_NO_OP_'BOOL_OP;OR;COMPOSITE_TEST;<Unused>;TEST @Value(_attr_name) = ReporterName'12'BOOL_OP;OR;COMPOSITE_TEST;<Unused>;TEST @Value(_attr_name) = ReporterPhone'13'BOOL_OP;OR;COMPOSITE_TEST;<Unused>;TEST @Value(_attr_name) = ReporterEmail'14'BOOL_OP;OR;COMPOSITE_TEST;<Unused>;TEST @Value(_attr_name) = Location'19'BOOL_OP;OR;COMPOSITE_TEST;<Unused>;TEST @Value(_attr_name) = MaterialsUsed'20'BOOL_OP;OR;COMPOSITE_TEST;<Unused>;TEST @Value(_attr_name) = Description'21'FME_NUM_CONDITIONS7___
      REMOVE _attr_name
      RENAME_SET_VALUE _attr_value > C
      REMOVE Description
      REMOVE MaterialsUsed
      REMOVE ReporterName
      REMOVE ReporterPhone
      REMOVE Location
      REMOVE ReporterEmail
    -> Work Order (writer XLSXW_1)

Bookmark: Create Excel Work Order
Work Order (writer XLSXW_1)
    attributes: C string(255)
