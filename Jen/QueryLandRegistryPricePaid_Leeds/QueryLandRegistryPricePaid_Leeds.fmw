FME workspace QueryLandRegistryPricePaid_Leeds.fmw
Title: QueryLandRegistryPricePaid_Leeds

Parameters:
- SourceDataset_ESRISHAPE = /tmp/wb_template_1523573241526_2563/1/UK World Tour/Leeds District (B).shp   # Source Esri Shapefile(s)

Readers:
- ESRISHAPE_1: ESRISHAPE from $(SourceDataset_ESRISHAPE)

Leeds District (B) (reader ESRISHAPE_1)
    attributes: NAME char(60), postcode char(200), e char(200), n char(200)
    -> Tester
Tester
    BOOL_OP = AND
    TEST_CLAUSE = CASE_INSENSITIVE_TEST @Value(postcode) CONTAINS
    PASSED -> AttributeManager [off]
    FAILED -> StringSearcher
StringSearcher
    CASE = no
    MATCHED_PARTS_ATTR = _matched
    MATCHED_RESULT_ATTR = match_
    REGEXP = .{3}$
    STRING_TO_SEARCH = @Value(postcode)
    MATCHED -> StringReplacer
StringReplacer
    CASE = NO
    FIND_TEXT = @Value(match_)
    NO_MATCH = _FME_NO_OP_
    REGEXP = NO
    REPLACE_TEXT = " @Value(match_)"
    SRC_ATTRS = postcode
    -> AttributeManager
HTTPCaller
    ADDITIONAL_URL_PARAMETERS = q;@Value(_encoded) output;json
    CONNECTION_TIMEOUT_LENGTH = 60
    ERROR_ATTR = _error
    FOLLOW_REDIRECTS = Yes
    HTTP_METHOD = POST
    SAVE_FILE = Attribute
    STATUS_CODE_ATTR = _http_status_code
    TARGET_ATTR = _response_body
    TARGET_ATTR_ENCODING = auto-detect
    TARGET_URL = http://landregistry.data.gov.uk/app/root/qonsole/query
    TRANSFER_TIMEOUT_LENGTH = 90
    UPLOAD_CONTENT_TYPE = Text (text/plain)
    UPLOAD_TYPE = Specify Upload Body
    USE_COOKIES = No
    VERIFY_SSL_CERTIFICATES = Yes
    -> JSONExtractor
DateTimeConverter_Output: Inspector [off]
JSONExtractor_Evaluated: Inspector [off]

Bookmark: Query Land Registery Price Paid
AttributeManager
    ATTR_TABLE:
      SET_TO Postcode = @UpperCase(@Value(postcode))
      SET_TO q = prefix rdf: <http://www.w3.org/1999/02/22-rdf-syntax-ns#>
        prefix rdfs: <http://www.w3.org/2000/01/rdf-schema#>
        prefix owl: <http://www.w3.org/2002/07/owl#>
        prefix xsd: <http://www.w3.org/2001/XMLSchema#>
        prefix sr: <http://data.ordnancesurvey.co.uk/ontology/spatialrelations/>
        prefix ukhpi: <http://landregistry.data.gov.uk/def/ukhpi/>
        prefix lrppi: <http://landregistry.data.gov.uk/def/ppi/>
        prefix skos: <http://www.w3.org/2004/02/skos/core#>
        prefix lrcommon: <http://landregistry.data.gov.uk/def/common/>

        # Returns the Price Paid data from the default graph for each transaction record having
        # an address with the given postcode.
        # The postcode to query is set using SPARQL 1.1's 'values' clause

        SELECT ?paon ?saon ?street ?town ?county ?postcode ?amount ?date ?category
        WHERE
        {
          VALUES ?postcode {"@Value(Postcode)"^^xsd:string}

          ?addr lrcommon:postcode ?postcode.

          ?transx lrppi:propertyAddress ?addr ;
                  lrppi:pricePaid ?amount ;
                  lrppi:transactionDate ?date ;
                  lrppi:transactionCategory/skos:prefLabel ?category.

          OPTIONAL {?addr lrcommon:county ?county}
          OPTIONAL {?addr lrcommon:paon ?paon}
          OPTIONAL {?addr lrcommon:saon ?saon}
          OPTIONAL {?addr lrcommon:street ?street}
          OPTIONAL {?addr lrcommon:town ?town}
        }
        ORDER BY ?amount
    -> TextEncoder
TextEncoder
    DEST_ATTR = _encoded
    ENCODING_TYPE = URL_ENCODE
    STRING_TO_ENCODE = @Value(q)
    -> HTTPCaller
JSONExtractor
    EXTRACT_QUERY_TABLE = _results json["result"]
    JSON_DOCUMENT = @Value(_response_body)
    EVALUATED -> JSONFragmenter [off]
    EVALUATED -> JSONExtractor_Evaluated
JSONFragmenter
    EXPLODE_FORMAT = JSON
    EXTRACT_ATTR = Yes
    JSON_ATTR = _results
    JSON_QUERY = json["results"]["bindings"][*]
    NEW_ATTRIBUTES = date.value hpi.value region.value
    RECURSIVE = Yes
    REJECT_EMPTY_LISTS = YES
    FRAGMENTS -> AttributeManager_2
AttributeManager_2
    ATTR_TABLE:
      REMOVE q
      REMOVE _encoded
      REMOVE _response_body
      REMOVE _http_status_code
      REMOVE _results
      REMOVE json_type
      REMOVE json_index
      RENAME_SET_VALUE date.value > Date
      RENAME_SET_VALUE hpi.value > HPI
      RENAME_SET_VALUE region.value > Region
    -> DateTimeConverter
DateTimeConverter
    DATETIME_ATTR = Date
    OUT_FORMAT = %Y%m%d
    REPAIR_INPUT = NO
    -> DateTimeConverter_Output
