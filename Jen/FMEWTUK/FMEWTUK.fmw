FME workspace FMEWTUK.fmw

Parameters:
- SourceDataset_ESRISHAPE = /Users/jlutherthomas/Desktop/UK World Tour/City of Edinburgh.shp   # Source Esri Shapefile(s)
- SourceDataset_GEOPACKAGE = /Users/jlutherthomas/Desktop/FMEWT_Cities.gpkg   # GeoPackage File
- DestDataset_POWERPOINT = /Users/jlutherthomas/Desktop/test.pptx   # Destination Microsoft PowerPoint file

Readers:
- ESRISHAPE_1: ESRISHAPE from $(SourceDataset_ESRISHAPE)
- GEOPACKAGE_1: GEOPACKAGE from $(SourceDataset_GEOPACKAGE)

Writers:
- POWERPOINT_1: POWERPOINT to $(DestDataset_POWERPOINT)

FMEWT_Cities (reader GEOPACKAGE_1)
    attributes: id int, fmewt stop text(200), City text(15), Venue text(200), Address text(200)
    -> Tester
Tester
    BOOL_OP = AND
    TEST_CLAUSE = CASE_INSENSITIVE_TEST @Value(City) = Nottingham
    PASSED -> Bufferer
    PASSED -> Junction
Presentation (writer POWERPOINT_1)
    attributes: id text, fmewt stop text, City text, Venue text, Address text, ID text, FEATCODE text, CLASSIFICA text, DISTNAME text, ROADNUMBER text, DRAWLEVEL text, OVERRIDE text

Bookmark: Get Map Data
Bufferer
    ANGLE = 22.5
    CAP_STYLE = Round
    CORNER_STYLE = Round
    MODE = AREA
    OFFSET = 500
    BUFFERED -> BoundingBoxReplacer
BoundingBoxReplacer
    BOXTYPE = Bounding Box
    BOX -> FeatureReader [INITIATOR]
FeatureReader
    ATTRIBUTES = SK_AdministrativeBoundary,"ID,CLASSIFICA,FEATCODE,fme_basename,fme_dataset,fme_feature_type",SK_Building,"ID,FEATCODE,fme_basename,fme_dataset,fme_feature_type",SK_ElectricityTransmissionLine,"ID,FEATCODE,fme_basename,fme_dataset,fme_feature_type",SK_Foreshore,"ID,FEATCODE,fme_basename,fme_dataset,fme_feature_type",SK_FunctionalSite,"ID,DISTNAME,CLASSIFICA,FEATCODE,fme_basename,fme_dataset,fme_feature_type",SK_Glasshouse,"ID,FEATCODE,fme_basename,fme_dataset,fme_feature_type",SK_MotorwayJunction,"ID,JUNCTNUM,FEATCODE,fme_basename,fme_dataset,fme_feature_type",SK_NamedPlace,"ID,DISTNAME,HTMLNAME,CLASSIFICA,FONTHEIGHT,ORIENTATIO,FEATCODE,fme_basename,fme_dataset,fme_feature_type",SK_Ornament,"ID,FEATCODE,fme_basename,fme_dataset,fme_feature_type",SK_RailwayStation,"ID,DISTNAME,CLASSIFICA,FEATCODE,fme_basename,fme_dataset,fme_feature_type",SK_RailwayTrack,"ID,CLASSIFICA,FEATCODE,fme_basename,fme_dataset,fme_feature_type",SK_RailwayTunnel,"ID,FEATCODE,fme_basename,fme_dataset,fme_feature_type",SK_Road,"ID,DISTNAME,ROADNUMBER,CLASSIFICA,DRAWLEVEL,OVERRIDE,FEATCODE,fme_basename,fme_dataset,fme_feature_type",SK_RoadTunnel,"ID,FEATCODE,fme_basename,fme_dataset,fme_feature_type",SK_Roundabout,"ID,CLASSIFICA,FEATCODE,fme_basename,fme_dataset,fme_feature_type",SK_SpotHeight,"ID,HEIGHT,FEATCODE,fme_basename,fme_dataset,fme_feature_type",SK_SurfaceWater_Area,"ID,FEATCODE,fme_basename,fme_dataset,fme_feature_type",SK_SurfaceWater_Line,"ID,FEATCODE,fme_basename,fme_dataset,fme_feature_type",SK_TidalBoundary,"ID,CLASSIFICA,FEATCODE,fme_basename,fme_dataset,fme_feature_type",SK_TidalWater,"ID,FEATCODE,fme_basename,fme_dataset,fme_feature_type",SK_Woodland,"ID,FEATCODE,fme_basename,fme_dataset,fme_feature_type"
    ATTR_ACCUM_MODE = Merge Initiator and Result
    ATTR_CONFLICT_RES = Use Result
    COMBINE_GEOM = Use Result
    DATASET = /Users/jlutherthomas/Downloads/OS VectorMap District (ESRI Shape File) SK/data/*.shp
    ESRISHAPE_CHECK_NUMERIC_FIELDS = yes
    ESRISHAPE_DISSOLVE_HOLES = no
    ESRISHAPE_ESRISHAPE_EXPOSE_FORMAT_ATTRS = fme_basename,char(50) fme_dataset,char(50) fme_feature_type,char(50)
    ESRISHAPE_MEASURES_AS_Z = no
    ESRISHAPE_NUMERIC_TYPE_ATTRIBUTE_HANDLING = STANDARD_TYPES
    ESRISHAPE_REPORT_BAD_GEOMETRY = no
    ESRISHAPE_SIMPLE_DONUT_GEOMETRY = simple
    ESRISHAPE_TRIM_PRECEDING_SPACES = yes
    ESRISHAPE_UPPER_CASE_ATTR_NAMES = No
    ESRISHAPE_USE_SEARCH_ENVELOPE = NO
    FEATURETYPES = SK_Building SK_ElectricityTransmissionLine SK_RailwayStation SK_RailwayTrack SK_RailwayTunnel SK_Road SK_RoadTunnel SK_Roundabout
    FORMAT = ESRISHAPE
    INTERACT = Bounding Boxes Intersect
    OUTPUT_FEATURES_DISPLAY = Data Features
    SK_Building -> Junction
    SK_ElectricityTransmissionLine -> Junction
    SK_RailwayStation -> Junction
    SK_RailwayTrack -> Junction
    SK_RailwayTunnel -> Junction
    SK_Road -> Junction
    SK_RoadTunnel -> Junction
    SK_Roundabout -> Junction

Bookmark: New Bookmark
Junction
    -> PowerPointStyler
PowerPointStyler
    PARAMETER_SETUP = pptx_slide_subtype[WithTitle[pptx_title_text[@Value(City)[pptx_caption_text[<Unused>[LABEL_GROUP[FME_DISCLOSURE_OPEN[pptx_map_label["FME_CONDITIONAL:DEFAULT_VALUE''BOOL_OP;OR;COMPOSITE_TEST;<Unused>;TEST @Value(fme_basename) = FMEWT_Cities'@Value(Venue)'FME_NUM_CONDITIONS2___"[fme_pptx_font_data["Arial Black,18"[pptx_font_color[0,0,0[pptx_label_wrap[No[FILL_GROUP[FME_DISCLOSURE_OPEN[pptx_map_fill_pattern[[pptx_map_fill_fore_color["FME_CONDITIONAL:DEFAULT_VALUE'0,0,0'BOOL_OP;OR;COMPOSITE_TEST;<Unused>;CASE_INSENSITIVE_TEST @Value(fme_basename) CONTAINS road'0.6,0.4,0.2'BOOL_OP;OR;COMPOSITE_TEST;<Unused>;CASE_INSENSITIVE_TEST @Value(fme_basename) CONTAINS building'0.987976,0.352911,0.810803'FME_NUM_CONDITIONS3___"[pptx_map_fill_back_color["FME_CONDITIONAL:DEFAULT_VALUE''BOOL_OP;OR;COMPOSITE_TEST;<Unused>;CASE_INSENSITIVE_TEST @Value(fme_basename) CONTAINS road'0.6,0.4,0.2'BOOL_OP;OR;COMPOSITE_TEST;<Unused>;CASE_INSENSITIVE_TEST @Value(fme_basename) CONTAINS building'0.987976,0.352911,0.810803'FME_NUM_CONDITIONS3___"[BORDER_GROUP[[pptx_map_border_style[[pptx_map_border_width[1[pptx_map_border_color[0,0,0[HYPERLINK_GROUP[[pptx_map_hyperlink[[pptx_merge_features[Yes[pptx_merge_id[@Value(City)[FME_CONTROLLER_QUERY_FILE[transformers/dependencies/powerpoint/slide_types/Map Slide.fme
    SLIDE_TYPE = Map Slide
    pptx_slide_order = 0
    -> Presentation (writer POWERPOINT_1)

Bookmark: Title Slide
Creator
    GEOMTYPE = Geometry Object
    NUM = 1
    CREATED -> PowerPointStyler_2
PowerPointStyler_2
    PARAMETER_SETUP = pptx_slide_subtype[WithTitle[pptx_title_text[FME World Tour Nottingham[pptx_caption_text[<Unused>[pptx_image_fit[BestFit[pptx_image_source[FromFile[pptx_image_filename[/Users/jlutherthomas/Dropbox (Safe Software Inc.)/Screenshots/Screenshot 2018-04-18 14.27.31.png[HYPERLINK_GROUP[[pptx_hyperlink[[FME_CONTROLLER_QUERY_FILE[transformers/dependencies/powerpoint/slide_types/Image Slide.fme
    SLIDE_TYPE = Image Slide
    pptx_slide_order = 0
    -> Presentation (writer POWERPOINT_1)
