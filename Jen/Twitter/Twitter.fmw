FME workspace Twitter.fmw
Title: QueryLandRegistryPricePaid

Parameters:
- DestDataset_HTML = /Users/jlutherthomas/Desktop/Desserts.html   # HTML Files(*.html)|*.html Destination Html File

Writers:
- HTML_1: HTML to $(DestDataset_HTML)

HTMLReportGenerator
    CONTENT_LIST = HEADER IMAGE HEADER
    GROUP_BY = _tweet_id
    PAGE_CONFIG = HEADER{{TEXT;@Value(_tweet_status);HEADER;H1;ALIGNMENT;CENTER;COLOR;0,0,0;FME_CONTROLLER_QUERY_FILE;transformers/dependencies/html5/Header.fme}}IMAGE{{AT;LINK;URL;@Value(match{0}.match);PATH;<Unused>;ALT_TEXT;;FME_CONTROLLER_QUERY_FILE;transformers/dependencies/html5/Image.fme}}HEADER{{TEXT;Tweet by @@Value(_tweet_username);HEADER;H5;ALIGNMENT;CENTER;COLOR;0,0,0;FME_CONTROLLER_QUERY_FILE;transformers/dependencies/html5/Header.fme}}
    TITLE = Team Pinks desserts 2018
    -> ModuloCounter
HTML (writer HTML_1)
    attributes: html_content buffer

Bookmark: 1. Collect the last 50 tweets
Creator
    GEOMTYPE = Geometry Object
    NUM = 1
    CREATED -> TiaAtSafe
    CREATED -> DaleAtSafe
    CREATED -> Mapgirll
TiaAtSafe: TwitterStatusFetcher
    TWITTER_CONNECTION = mapgirll Twitter
    TWITTER_REQUEST_TYPE = User
    TWITTER_STATUS_COUNT = 50
    TWITTER_TIMELINE = tiaatsafe
    TWEETS -> TestFilter
DaleAtSafe: TwitterStatusFetcher
    TWITTER_CONNECTION = mapgirll Twitter
    TWITTER_REQUEST_TYPE = User
    TWITTER_STATUS_COUNT = 50
    TWITTER_TIMELINE = daleatsafe
    TWEETS -> TestFilter
Mapgirll: TwitterStatusFetcher
    TWITTER_CONNECTION = mapgirll Twitter
    TWITTER_REQUEST_TYPE = User
    TWITTER_STATUS_COUNT = 50
    TWITTER_TIMELINE = mapgirll
    TWEETS -> TestFilter

Bookmark: 2. Find tweets that mention dessert
TestFilter
    DEFAULT_VALUE = No Dessert
    TEST_LIST:
      "BOOL_OP,COMPOSITE,COMPOSITE_TEST,""""""(1 OR 2 OR 3 OR 4 OR 5 OR 6 OR 7 OR 8) AND 9"""""",TEST_CLAUSE,CASE_INSENSITIVE_TEST @Value(_tweet_status) CONTAINS dessert
      CASE_INSENSITIVE_TEST @Value(_tweet_status) CONTAINS cake
      CASE_INSENSITIVE_TEST @Value(_tweet_status) CONTAINS pudding
      CASE_INSENSITIVE_TEST @Value(_tweet_status) CONTAINS ice cream
      CASE_INSENSITIVE_TEST @Value(_tweet_status) CONTAINS churros
      CASE_INSENSITIVE_TEST @Value(_tweet_status) CONTAINS berry
      CASE_INSENSITIVE_TEST @Value(_tweet_status) CONTAINS sweet
      CASE_INSENSITIVE_TEST @Value(_tweet_status) CONTAINS torte
      CASE_SENSITIVE_TEST @Value(_tweet_status) NOT_BEGINS_WITH RT ",Dessert
    Dessert -> StringSearcher

Bookmark: 3. Get image url and download it
StringSearcher
    CASE = no
    MATCHED_PARTS_ATTR = _matched
    MATCHES_ATTR = match
    REGEXP = http://pbs.twimg.com/media/.*?.jpg
    STRING_TO_SEARCH = @Value(_tweet_search_result)
    MATCHED -> ImageFetcher
ImageFetcher
    CONNECTION_TIMEOUT_LENGTH = 60
    ERROR_ATTR = _http_error
    FOLLOW_REDIRECTS = Yes
    RASTER_TYPE = JPEG
    RESPONSE_HEADER_LIST_ATTR = _http_headers
    STATUS_CODE_ATTR = _http_status_code
    TRANSFER_TIMEOUT_LENGTH = 90
    URL = @Value(match{0}.match)
    USE_COOKIES = No
    VERIFY_SSL_CERTIFICATES = Yes
    RASTER -> HTMLReportGenerator

Bookmark: 5. Grid layout HTML
ModuloCounter
    CNT_ATTR = _modulo_count
    DOMAIN = modcounter
    MOD = 2
    -> TestFilter_2
TestFilter_2
    DEFAULT_VALUE = 0
    TEST_LIST = "BOOL_OP,OR,COMPOSITE_TEST,""""""<Unused>"""""",TEST_CLAUSE,TEST @Value(_modulo_count) = 1",1
    1 -> Counter
    0 -> Counter_2
Counter
    CNT_ATTR = _count
    DOMAIN = counter
    SCOPE = Local
    START = 1
    -> HTMLLayouter
Counter_2
    CNT_ATTR = _count
    DOMAIN = counter
    SCOPE = Local
    START = 1
    -> HTMLLayouter
HTMLLayouter
    COLUMN = @Value(_modulo_count)
    DIV_STYLE = NONE
    LAYOUT = GRID
    ROW = @Value(_count)
    -> HTML (writer HTML_1)
