FME workspace PDFSimpleDemo_Server.fmw

Parameters:
- SourceDataset_PDF2D = /Users/dmurray/Dropbox (Safe Software Inc.)/DonStuffMac/DonStuff/DemoData/FME2018/FME2018ServerDeepDive/Automation/data/US_County_Populations.pdf   # Source Adobe Geospatial PDF File
- DestDataset_ESRISHAPE = /Users/dmurray/Dropbox (Safe Software Inc.)/DonStuffMac/DonStuff/DemoData/FME2018/FME2018ServerDeepDive/Automation/output   # Destination Esri Shapefile Folder

Readers:
- PDF2D_1: PDF2D from $(SourceDataset_PDF2D)

Writers:
- ESRISHAPE_1: ESRISHAPE to $(DestDataset_ESRISHAPE)

Bookmark: PDF to Shape with Attributes!
County_Stats (reader PDF2D_1)
    attributes: AREA, CNTY_FIPS, FEMALES, FIPS, MALES, NAME, POP90_SQMI, POP1990, POP2000, STATE_FIPS, STATE_NAME, dden, den00, den90, female, male, xls_popden_class, xls_total
    -> Tester
Note: If FIPS code is missing, exclude (remove duplicate empty rows)
Tester
    BOOL_OP = OR
    TEST_CLAUSE = TEST CNTY_FIPS NOT_ATTRIBUTE_IS_MISSING ""
    PASSED -> AttributeManager
Note: Rename xls_popden_class to make shapefile friendly
AttributeManager
    ATTR_TABLE = RENAME_SET_VALUE xls_popden_class > xls_popden
    -> County_Stats (writer ESRISHAPE_1)
    -> Logger
County_Stats (writer ESRISHAPE_1)
    attributes: AREA char(200), CNTY_FIPS char(200), FEMALES char(200), FIPS char(200), MALES char(200), NAME char(200), POP90_SQMI char(200), POP1990 char(200), POP2000 char(200), STATE_FIPS char(200), STATE_NAME char(200), female char(200), male char(200), xls_popden char(200), xls_total char(200)
Logger
    LOG_FEATURE = LOG_ONLY
    MAXCOORDS = 20
    MAXFEATS = 20
    MESSAGE = Feature is:
    SEVERITY = INFO
