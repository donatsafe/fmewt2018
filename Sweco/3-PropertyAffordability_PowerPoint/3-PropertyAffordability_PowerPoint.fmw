FME workspace 3-PropertyAffordability_PowerPoint.fmw
Title: 3-PropertyAffordability_PowerPoint

Parameters:
- SourceStatsCanada = /Users/fme/Desktop/FMEWT 2018/Sweco/1 - Getting Started with FME 2018/demo ppt/3-PropertyAffordability_PowerPoint/sourceData/StatsCanadaCensusCanada.csv   # Source Stats Canada Census CSV File(s)
- SourceDataset_CSV2 = /Users/fme/Desktop/FMEWT 2018/Sweco/1 - Getting Started with FME 2018/demo ppt/3-PropertyAffordability_PowerPoint/sourceData/Simplified_Tax_Report.csv   # Source CSV (Comma Separated Value) File(s)
- SourceCensusDA_2 = /Users/fme/Desktop/FMEWT 2018/Sweco/1 - Getting Started with FME 2018/demo ppt/3-PropertyAffordability_PowerPoint/sourceData/StatsCanadaDisseminationAreasYVR.gdb   # Source Stats Canada Census DA TAB File
- SourceDataset_MAPINFO_EXTENDED_3 = /Users/fme/Desktop/FMEWT 2018/Sweco/1 - Getting Started with FME 2018/demo ppt/3-PropertyAffordability_PowerPoint/sourceData/PostCodeAreas.gdb   # Source MapInfo TAB File(s)
- DestDataset_POWERPOINT = /Users/fme/Desktop/FMEWT 2018/Sweco/1 - Getting Started with FME 2018/demo ppt/output/PropertyAffordability.pptx   # Destination Microsoft PowerPoint file

Readers:
- FILEGDB_1: FILEGDB from $(SourceCensusDA_2)
- CSV2_1: CSV2 from $(SourceStatsCanada)
- CSV2_2: CSV2 from $(SourceDataset_CSV2)
- FILEGDB_2: FILEGDB from $(SourceDataset_MAPINFO_EXTENDED_3)

Writers:
- POWERPOINT_1: POWERPOINT to $(DestDataset_POWERPOINT)

Presentation (writer POWERPOINT_1)

Bookmark: 1. Process Stats Canada Census Data
Note: CSV: StatsCanadaCensusCanada Census Data / Dissemination Areas
CSV (reader CSV2_1)
    attributes: CENSUS_YEAR uint16, GEO_CODE (POR) uint32, GEO_LEVEL uint8, GEO_NAME string, Total Pop 2016 uint32, Pop 2016 F uint32, Pop 2016 M uint32, Total Dwellings uint32, Pop Density per sq km real32, Land Area sq km real64, Average Age real32, Median Age real32, Average Income(CDN) uint32, Median Income (CDN) uint32, Median Income FT(CDN) uint32, Average Income FT(CDN) uint32, House Median Value(CDN) uint32, House Average Value(CDN uint32, Median Rental(CDN) uint16, Average Rental(CDN) uint16
    -> FeatureJoiner_3 [LEFT]
StatsCanadaDisseminationAreasYVR (reader FILEGDB_1)
    attributes: DAUID text(8), PRUID text(2), PRNAME text(100), CDUID text(4), CDNAME text(100), CDTYPE text(3), CCSUID text(7), CCSNAME text(100), CSDUID text(7), CSDNAME text(100), CSDTYPE text(3), ERUID text(4), ERNAME text(100), SACCODE text(3), SACTYPE text(1), CMAUID text(3), CMAPUID text(5), CMANAME text(100), CMATYPE text(1), CTUID text(10), CTNAME text(7), ADAUID text(8), OBJECTID objectid
    -> FeatureJoiner_3 [RIGHT]
FeatureJoiner_3
    ATTR_CONFLICT_RES = Use Left
    GEOMETRY_HANDLING = Use Right
    JOIN_KEYS = GEO_NAME DAUID AUTO
    JOIN_MODE = Inner
    JOINED -> PointOnAreaOverlayer [AREA]

Bookmark: 2. City of Vancouver Property Tax Data
Note: CSV: Simplified_Property_Tax_Report
CSV (reader CSV2_2)
    attributes: PID string, LEGAL_TYPE string, FOLIO string, LAND_COORDINATE string, ZONE_NAME string, ZONE_CATEGORY string, BLOCK string, PLAN string, DISTRICT_LOT string, STREET_NAME string, PROPERTY_POSTAL_CODE string, CURRENT_LAND_VALUE string, CURRENT_IMPROVEMENT_VALUE string, TAX_ASSESSMENT_YEAR string, PREVIOUS_LAND_VALUE string, PREVIOUS_IMPROVEMENT_VALUE string, TAX_LEVY string, NEIGHBOURHOOD_CODE string
    -> FeatureJoiner_4 [LEFT]
Note: City of Vancouver / zip code polygons
PostCodeAreas (reader FILEGDB_2)
    attributes: POSTALCODE text(9), STREETNAME text(80), OBJECTID objectid
    -> FeatureJoiner_4 [RIGHT]
FeatureJoiner_4
    ATTR_CONFLICT_RES = Use Left
    GEOMETRY_HANDLING = Use Right
    JOIN_KEYS = PROPERTY_POSTAL_CODE POSTALCODE AUTO
    JOIN_MODE = Inner
    JOINED -> CenterPointReplacer
CenterPointReplacer
    MODE = Center Point
    POINT -> PointOnAreaOverlayer [POINT]
PointOnAreaOverlayer
    CANDIDATE_LIST_ATTRS_TO_INCLUDE = CURRENT_LAND_VALUE
    CANDIDATE_LIST_ATTRS_TO_INCLUDE_MODE = Selected Attributes
    CANDIDATE_LIST_NAME = _propertyTax
    DEAGGREGATE_INPUT = Yes
    OV_ATTR = _related_candidates
    POLYS_FIRST = NO
    AREA -> ListSummer
ListSummer
    RESULT = _sum
    SRC_LIST = _propertyTax{}.CURRENT_LAND_VALUE
    -> AttributeCreator
AttributeCreator
    ATTR_TABLE:
      SET_TO 2017_ASSESSED_VALUE = @Evaluate(@Evaluate(@Value(_sum)/@Value(_related_candidates)))
      SET_TO incomeValueRatio = @Evaluate((@Value(_sum)/@Value(_related_candidates))/@Value(Median Income FT(CDN)))
      SET_TO incomeValueRatioLOG10 = @Evaluate(@log10((@Value(_sum)/@Value(_related_candidates))/@Value(Median Income FT(CDN))))
    -> 3DForcer
    -> Sorter

Bookmark: Prep Map Output
3DForcer
    KEEPZVAL = No
    ZVALATTR = @Value(incomeValueRatio)
    -> GradedColorizer
GradedColorizer
    Attribute_to_Color = @Evaluate(@log10(@Value(incomeValueRatio)))
    Binning_Method = C
    Color_Scheme = 8
    Number_of_Bands = 7
    RangeVals = 0,1,2,2.25,2.5,2.75,3
    -> PowerPointStyler
PowerPointStyler
    PARAMETER_SETUP = pptx_slide_subtype[WithTitle[pptx_title_text[Affordability Heatmap (Red=$$$)[pptx_caption_text[<Unused>[LABEL_GROUP[FME_DISCLOSURE_CLOSED[pptx_map_label[[fme_pptx_font_data[[pptx_font_color[[pptx_label_wrap[No[FILL_GROUP[FME_DISCLOSURE_OPEN[pptx_map_fill_pattern[[pptx_map_fill_fore_color[@Value(fme_fill_color)[pptx_map_fill_back_color[[BORDER_GROUP[[pptx_map_border_style[[pptx_map_border_width[1[pptx_map_border_color[0,0,0[HYPERLINK_GROUP[[pptx_map_hyperlink[[pptx_merge_features[Yes[pptx_merge_id[a[FME_CONTROLLER_QUERY_FILE[transformers/dependencies/powerpoint/slide_types/Map Slide.fme
    SLIDE_TYPE = Map Slide
    pptx_slide_order = 0
    -> Presentation (writer POWERPOINT_1)

Bookmark: Prep Top 5 Table
Sorter
    SORT_PARM = incomeValueRatio NUMERIC DESCENDING
    SORTED -> Sampler
Sampler
    RATE = 5
    SAMPLE_MODE = No
    SAMPLE_TYPE_LONG = First N Features
    SAMPLED -> PythonCaller
PythonCaller
    PYTHONSOURCE:
      import fme

      import fmeobjects

      # Format two attribute nicely as currency

      def FeatureProcessor(feature):

          for attr in ['2017_ASSESSED_VALUE','Average Income(CDN)']:

              value = feature.getAttribute(attr) or ''
              try:
                  value_str = "${:,.2f}".format(value)
              except ValueError, TypeError:
                  value_str = value
              feature.setAttribute(attr, value_str)
    PYTHONSYMBOL = FeatureProcessor
    -> ListBuilder
ListBuilder
    GROUPS_ORDERED = No
    LIST_ATTRS_TO_INCLUDE = 2017_ASSESSED_VALUE Average Income(CDN) Total Pop 2016 incomeValueRatio
    LIST_NAME = _mostExpensive
    -> PowerPointStyler_2
PowerPointStyler_2
    PARAMETER_SETUP = pptx_title_text[Top 5 Most Unaffordable[pptx_table_style["Medium Style 2 Accent 1"[pptx_table_banding[Yes[pptx_measurement_units[Inches[fme_pptx_table_data[Land Value}_mostExpensive{}.2017_ASSESSED_VALUE}Stretch}Average Income}_mostExpensive{}.Average Income(CDN)}Stretch}Population}_mostExpensive{}.Total Pop 2016}Stretch[FME_CONTROLLER_QUERY_FILE[transformers/dependencies/powerpoint/slide_types/Table Slide.fme
    SLIDE_TYPE = Table Slide
    pptx_slide_order = 1
    -> Presentation (writer POWERPOINT_1)

FME custom transformer GradedColorizer
Colors features along a delineated range of colors based on the values of a numerical attribute.
This transformer has five parameters:
    Attribute to Classify on: Here you select a numerical attribute which the feature colors will be based on
    Color Scheme: Here you select the color gradient you wish the features to follow
    Classification Method: Here you select the method used to classify the features, four options are available:
    Set Intervals- in this option intervals are determined by user entered numerical values in the Interval Break Values Parameter
    Equal Intervals- creates a user specified number of intervals of equal length based on the range of the numerical attribute
    Quantile- creates a user specified number of intervals where features are uniformly distributed over intervals 
    Unique Values- Each group will contain features with the same classification attribute value
    Number of Intervals: Here you specify the number of intervals (Ignored if Classification method is set intervals or Unique Values)
    Interval Break Values: Here you enter the interval break points as a space delimited string (Ignored if Classification method is not set intervals) Eg. '0 10 20 30 40'

Parameters:
- Attribute_to_Color =   # Attribute to Color on
- Color_Scheme = 1   # Rainbow,2%Red to White,3%White to Red,4%Blue to White,5%White to Blue,6%Red to Green,7%Green to Red,8 Color Scheme
- Binning_Method = B   # Set Intervals,A%Equal Intervals,B%Quantile,C%Unique Values,D Classification Method
- Number_of_Bands = 4   # Number of Intervals
- RangeVals =   # Interval Break Values

INPUT (input)
    -> ParameterFetcher_2
AttributeRemover
    REMOVE_ATTRS = GC_Binning_Method,GC_Number_of_Bands,GC_min,GC_RangeVals,GC_tcount,GC_Value,GC_Color_Scheme,GC_range,rval,_stdevp,_part_number,GC_count,_geometry_name
    -> AttributeExposer
AttributeExposer
    ATTR_LIST = fme_color,fme_fill_color
    -> OUTPUT (output)
OUTPUT (output)

Bookmark: Pull Parameters into Attributes
ParameterFetcher_2
    ATTR_LIST = GC_Number_of_Bands {$(Number_of_Bands)} GC_Color_Scheme {$(Color_Scheme)} GC_RangeVals {$(RangeVals)} GC_Value {$(Attribute_to_Color)} GC_Binning_Method {$(Binning_Method)}
    -> TestFilter

Bookmark: Branch based on Classification Method
TestFilter
    DEFAULT_VALUE = <UNFILTERED>
    TEST_LIST = BOOL_OP,OR,COMPOSITE_TEST,<Unused>,TEST_CLAUSE,"TEST @Value(GC_Binning_Method) = A",Binning_Method = A,BOOL_OP,OR,COMPOSITE_TEST,<Unused>,TEST_CLAUSE,"TEST @Value(GC_Binning_Method) = B",Binning_Method = B,BOOL_OP,OR,COMPOSITE_TEST,<Unused>,TEST_CLAUSE,"TEST @Value(GC_Binning_Method) = C",Binning_Method = C,BOOL_OP,OR,COMPOSITE_TEST,<Unused>,TEST_CLAUSE,"TEST @Value(GC_Binning_Method) = D",Binning_Method = D
    Binning_Method = A -> PythonCaller_4
    Binning_Method = B -> StatisticsCalculator
    Binning_Method = C -> StatisticsCalculator_2
    Binning_Method = D -> Aggregator

Bookmark: Calculate RGB based on specified Intervals
PythonCaller_4
    PYTHONSOURCE:
      import fmeobjects, math, colorsys
      # Template Function interface:
      def processFeature(feature):
         pass

      # Template Class Interface:
      class FeatureProcessor(object):
         def __init__(self):
             pass
         def input(self,feature):

             # Get interval break values
             rval=feature.getAttribute("GC_RangeVals")

             # Number of groups = number of break values plus 1
             bands=len(rval.split())+1;

             # Get color scheme and attribute to color on, also initialize variables
             Value=float(feature.getAttribute("GC_Value"))
             cs=int(feature.getAttribute("GC_Color_Scheme"))
             R=0.0
             G=0.0
             B=0.0
             global bin
             i=0

             # for each value in the input list of break values
             for val in rval.split():

                 # Check if the attribute value is less than or equal to the break value used in this iteration
                 if Value<=float(val):
                     # Set the feature's color
                     [R,G,B]=self.color(i,cs,bands)
                     feature.setAttribute("fme_color",str(R)+","+str(G)+","+str(B))
                     feature.setAttribute("fme_fill_color",str(R)+","+str(G)+","+str(B))
                     break
                 # If the attribute value is greater than the last break value, then it should be in the last group
                 elif Value>float(rval.split()[-1]):
                     # Set the feature's color
                     [R,G,B]=self.color(bands,cs,bands+1)
                     feature.setAttribute("fme_color",str(R)+","+str(G)+","+str(B))
                     feature.setAttribute("fme_fill_color",str(R)+","+str(G)+","+str(B))
                     break
                 # if we have reached here, the attribute value has not been less than or equal to the current break value and
                 # has not been greater than the last break value. It does not belong to group i, so it might belong to group i+1
                 i=i+1
             self.pyoutput(feature)
         def close(self):
             pass

         # This function sets feature's color based on the group it belongs to, the number of groups, and color scheme
         def color(self,i,cs,bands):
                     if (bands!=1):
                          bands-=1
                     if cs==1:
                          [R,G,B]=colorsys.hsv_to_rgb(float(i)/bands,1,1)
                     elif cs==2:
                          [R,G,B]=colorsys.hsv_to_rgb(1-float(i)/bands,1,1)
                     elif cs==3:
                          [R,G,B]=[1,float(i)/bands,float(i)/bands]
                     elif cs==4:
                          [R,G,B]=[1,1-float(i)/bands,1-float(i)/bands]
                     elif cs==5:
                          [R,G,B]=[float(i)/bands,float(i)/bands,1]
                     elif cs==6:
                          [R,G,B]=[1-float(i)/bands,1-float(i)/bands,1]
                     elif cs==7:
                          [R,G,B]=colorsys.hsv_to_rgb(float(i)/bands/3,1,1)
                     elif cs==8:
                          [R,G,B]=colorsys.hsv_to_rgb(1.0/3-float(i)/bands/3,1,1)
                     else:
                         [R,G,B]=[0,0,0]
                     return [R,G,B]
    PYTHONSYMBOL = FeatureProcessor
    -> AttributeRemover

Bookmark: Calculate RGB based on Equal Intervals
Note: Find minimum and range / of attribute values
StatisticsCalculator
    COMPUTE_HISTOGRAM = NO
    MIN_ATTR = GC_min
    PREPEND_ATTR_NAME_CHOICE = For multiple results only
    RANGE_ATTR = GC_range
    STATS_ATTRS = GC_Value
    STDEVP_ATTR = _stdevp
    COMPLETE -> PythonCaller_2
PythonCaller_2
    PYTHONSOURCE:
      import fmeobjects, math, colorsys
      # Template Function interface:
      def processFeature(feature):
         pass

      # Template Class Interface:
      class FeatureProcessor(object):
         def __init__(self):
             pass
         def input(self,feature):

             # Get all needed attributes and initialize variables
             bands=int(feature.getAttribute("GC_Number_of_Bands"))
             min=float(feature.getAttribute("GC_min"))
             valrange=float(feature.getAttribute("GC_range"))
             Value=float(feature.getAttribute("GC_Value"))
             cs=int(feature.getAttribute("GC_Color_Scheme"))
             R=0.0
             G=0.0
             B=0.0
             global bin

             # Check attribute value to determine which interval it falls into. Then assign color accordingly
             for i in range(bands):
                 if Value<=min+float(i+1)*float(valrange)/bands:
                     [R,G,B]=self.color(i,cs,bands)
                     feature.setAttribute("fme_color",str(R)+","+str(G)+","+str(B))
                     feature.setAttribute("fme_fill_color",str(R)+","+str(G)+","+str(B))
                     break

             self.pyoutput(feature)
         def close(self):
             pass

         # This function sets feature's color based on the group it belongs to, the number of groups, and color scheme
         def color(self,i,cs,bands):
                     if (bands!=1):
                          bands-=1
                     if cs==1:
                          [R,G,B]=colorsys.hsv_to_rgb(float(i)/bands,1,1)
                     elif cs==2:
                          [R,G,B]=colorsys.hsv_to_rgb(1-float(i)/bands,1,1)
                     elif cs==3:
                          [R,G,B]=[1,float(i)/bands,float(i)/bands]
                     elif cs==4:
                          [R,G,B]=[1,1-float(i)/bands,1-float(i)/bands]
                     elif cs==5:
                          [R,G,B]=[float(i)/bands,float(i)/bands,1]
                     elif cs==6:
                          [R,G,B]=[1-float(i)/bands,1-float(i)/bands,1]
                     elif cs==7:
                          [R,G,B]=colorsys.hsv_to_rgb(float(i)/bands/3,1,1)
                     elif cs==8:
                          [R,G,B]=colorsys.hsv_to_rgb(1.0/3-float(i)/bands/3,1,1)
                     else:
                         [R,G,B]=[0,0,0]
                     return [R,G,B]
    PYTHONSYMBOL = FeatureProcessor
    -> AttributeRemover

Bookmark: Calculate RGB based on Quantile
Note: Count the number / of input features
StatisticsCalculator_2
    COMPUTE_HISTOGRAM = NO
    COUNT_ATTR = GC_tcount
    PREPEND_ATTR_NAME_CHOICE = For multiple results only
    STATS_ATTRS = GC_Value
    STDEVP_ATTR = _stdevp
    COMPLETE -> Sorter
Note: Sort features by their / attribute value
Sorter
    SORT_PARM = GC_Value NUMERIC ASCENDING
    SORTED -> Counter
Note: Put IDs on features / ID for first =0 / ID for last = total count-1
Counter
    CNT_ATTR = GC_count
    DOMAIN = counter
    SCOPE = Global
    START = 0
    -> PythonCaller_3
PythonCaller_3
    PYTHONSOURCE:
      import fmeobjects, math, colorsys
      # Template Function interface:
      def processFeature(feature):
         pass

      # Template Class Interface:
      class FeatureProcessor(object):
         def __init__(self):
             global bin
             bin=0
             global preval
             preval=0
             pass
         def input(self,feature):

             # Get all needed attributes and initialize variables
             bands=int(feature.getAttribute("GC_Number_of_Bands"))
             Value=float(feature.getAttribute("GC_Value"))
             count=int(feature.getAttribute("GC_count"))
             tcount=int(feature.getAttribute("GC_tcount"))
             cs=int(feature.getAttribute("GC_Color_Scheme"))
             R=0.0
             G=0.0
             B=0.0
             global bin

             # If feature ID is less than the current group number times number of items in each group,
             # the feature belongs to current group
             if count<(bin+1)*tcount/bands:
                  [R,G,B]=self.color(bin,cs,bands)
             # If not, the feature belongs to the next group
             else:
                  [R,G,B]=self.color(bin+1,cs,bands)
                  bin=bin+1
             feature.setAttribute("fme_color",str(R)+","+str(G)+","+str(B))
             feature.setAttribute("fme_fill_color",str(R)+","+str(G)+","+str(B))
             self.pyoutput(feature)
         def close(self):
             pass

         # This function sets feature's color based on the group it belongs to, the number of groups, and color scheme
         def color(self,i,cs,bands):
                     if (bands!=1):
                          bands-=1
                     if cs==1:
                          [R,G,B]=colorsys.hsv_to_rgb(float(i)/bands,1,1)
                     elif cs==2:
                          [R,G,B]=colorsys.hsv_to_rgb(1-float(i)/bands,1,1)
                     elif cs==3:
                          [R,G,B]=[1,float(i)/bands,float(i)/bands]
                     elif cs==4:
                          [R,G,B]=[1,1-float(i)/bands,1-float(i)/bands]
                     elif cs==5:
                          [R,G,B]=[float(i)/bands,float(i)/bands,1]
                     elif cs==6:
                          [R,G,B]=[1-float(i)/bands,1-float(i)/bands,1]
                     elif cs==7:
                          [R,G,B]=colorsys.hsv_to_rgb(float(i)/bands/3,1,1)
                     elif cs==8:
                          [R,G,B]=colorsys.hsv_to_rgb(1.0/3-float(i)/bands/3,1,1)
                     else:
                         [R,G,B]=[0,0,0]
                     return [R,G,B]
    PYTHONSYMBOL = FeatureProcessor
    -> AttributeRemover

Bookmark: Group and sort based on unique values
Aggregator
    ACCUM_ATTRS_NAME = Yes
    AGGREGATE_TYPE = Homogeneous Collection (If Possible)
    GROUP_BY = GC_Value
    LIST_NAME = list
    MODE = Geometry - Assemble One Level
    ORDERED = No
    SEP = ,
    AGGREGATE -> Sorter_2
Sorter_2
    SORT_PARM = GC_Value NUMERIC ASCENDING
    SORTED -> Aggregator_2

Bookmark: Concatenate Unique Values and store in attribute
Aggregator_2
    ACCUM_ATTRS_NAME = Yes
    AGGREGATE_TYPE = Homogeneous Collection (If Possible)
    CONCAT_ATTRS = GC_Value
    LIST_NAME = list
    MODE = Geometry - Assemble One Level
    ORDERED = No
    SEP = " "
    AGGREGATE -> AttributeRenamer
AttributeRenamer
    ATTR_TABLE = RENAME_SET_DEFAULT GC_Value > rval = @Value(GC_Value)
    -> Deaggregator

Bookmark: Deaggregate to get features back
Deaggregator
    ATTR_ACCUM_MODE = Merge List Attributes
    ATTR_CONFLICT_RES = Use List Attribute Values
    EXPLODE_INSTANCES = No
    GEOM_NAME_FIELD = _geometry_name
    LIST_ATTR = list{}
    LIST_ATTR_MODE_LOOKUP = LEAN
    MODE = Flatten One Level
    PART_NUMBER_FIELD = _part_number
    SPLIT_COMPOSITES = No
    DEAGGREGATED -> Deaggregator_2
Deaggregator_2
    ATTR_ACCUM_MODE = Merge List Attributes
    ATTR_CONFLICT_RES = Use List Attribute Values
    EXPLODE_INSTANCES = No
    GEOM_NAME_FIELD = _geometry_name
    LIST_ATTR = list{}
    LIST_ATTR_MODE_LOOKUP = LEAN
    MODE = Flatten One Level
    PART_NUMBER_FIELD = _part_number
    SPLIT_COMPOSITES = No
    DEAGGREGATED -> PythonCaller_5

Bookmark: Colorize
PythonCaller_5
    PYTHONSOURCE:
      import fmeobjects, math, colorsys
      # Template Function interface:
      def processFeature(feature):
         pass

      # Template Class Interface:
      class FeatureProcessor(object):
         def __init__(self):
             pass
         def input(self,feature):

             # Get the list of Unique Values
             rval=feature.getAttribute("rval")

             # Number of groups = number of Unique values
             bands=len(rval.split());

             # Get color scheme and attribute to color on, also initialize variables
             Value=float(feature.getAttribute("GC_Value"))
             cs=int(feature.getAttribute("GC_Color_Scheme"))
             R=0.0
             G=0.0
             B=0.0
             global bin
             i=0

             # for each value in the input list of unique values
             for val in rval.split():

                 # Check if the attribute value is equal to the break value used in this iteration
                 if Value==float(val):
                     [R,G,B]=self.color(i,cs,bands)
                     break

                 # if we have reached here, the attribute value has not been equal to the current unique value
                 # It does not belong to group i, so it might belong to group i+1
                 i=i+1

             # Set the feature's color
             feature.setAttribute("fme_color",str(R)+","+str(G)+","+str(B))
             feature.setAttribute("fme_fill_color",str(R)+","+str(G)+","+str(B))


             self.pyoutput(feature)
         def close(self):
             pass

         # This function sets feature's color based on the group it belongs to, the number of groups, and color scheme
         def color(self,i,cs,bands):
                     if (bands!=1):
                          bands-=1
                     if cs==1:
                          [R,G,B]=colorsys.hsv_to_rgb(float(i)/bands,1,1)
                     elif cs==2:
                          [R,G,B]=colorsys.hsv_to_rgb(1-float(i)/bands,1,1)
                     elif cs==3:
                          [R,G,B]=[1,float(i)/bands,float(i)/bands]
                     elif cs==4:
                          [R,G,B]=[1,1-float(i)/bands,1-float(i)/bands]
                     elif cs==5:
                          [R,G,B]=[float(i)/bands,float(i)/bands,1]
                     elif cs==6:
                          [R,G,B]=[1-float(i)/bands,1-float(i)/bands,1]
                     elif cs==7:
                          [R,G,B]=colorsys.hsv_to_rgb(float(i)/bands/3,1,1)
                     elif cs==8:
                          [R,G,B]=colorsys.hsv_to_rgb(1.0/3-float(i)/bands/3,1,1)
                     else:
                         [R,G,B]=[0,0,0]
                     return [R,G,B]
    PYTHONSYMBOL = FeatureProcessor
    -> AttributeRemover
