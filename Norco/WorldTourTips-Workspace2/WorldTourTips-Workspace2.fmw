FME workspace WorldTourTips-Workspace2.fmw
Title: WorldTourTips-Workspace1

Parameters:
- SourceDataset_FILEGDB = /Users/fme/Desktop/FMEWT 2018/Nokart/Tips & Tricks/Demos/wt2018/WorldTourTips-Workspace1/1/Addresses/Addresses.gdb   # File Geodatabase
- SourceDataset_MITAB = /Users/fme/Desktop/FMEWT 2018/Nokart/Tips & Tricks/Demos/wt2018/WorldTourTips-Workspace1/1/Zoning/Zones.tab   # Source MapInfo TAB File(s)
- DestDataset_GEOPACKAGE = /Users/fme/Desktop/FMEWT 2018/Nokart/Tips & Tricks/Demos/wt2018/Output/C:\FMEData2018\Output\Training\GarbageZones.gpkg   # GeoPackage File

Readers:
- FILEGDB_1: FILEGDB from $(SourceDataset_FILEGDB)
- MITAB_1: MITAB from $(SourceDataset_MITAB)

Writers:
- GEOPACKAGE_1: GEOPACKAGE to $(DestDataset_GEOPACKAGE)

Bookmark: Addresses
PostalAddress (reader FILEGDB_1)
    attributes: OBJECTID objectid, GlobalID guid, OWNERNM1 text(150), OWNERNM2 text(150), PSTLADDRESS text(250), PSTLCITY text(100), PSTLPROV text(25), INTSTATE text(5), INTPSTLCD text(10), COUNTRY text(100), REPRESENT text(14), STATUS text(9), LASTUPDATE date, LASTEDITOR text(50), POSTALCODE text(6)
    -> Sampler

Bookmark: Sample Addresses
Sampler
    RATE = 25
    SAMPLE_MODE = No
    SAMPLE_TYPE_LONG = Every Nth Feature
    SAMPLED -> PointOnAreaOverlayer [POINT]

Bookmark: Zoning
Zones (reader MITAB_1)
    attributes: ZoneName char(30), ZoneCategory char(30)
    -> PointOnAreaOverlayer [AREA]

Bookmark: Spatial Join
PointOnAreaOverlayer
    ATTR_ACCUM_MODE = Merge Incoming
    ATTR_CONFLICT_RES = Use Original
    DEAGGREGATE_INPUT = Yes
    OV_ATTR = _overlaps
    POLYS_FIRST = NO
    POINT -> AttributeManager

Bookmark: Calculate Residents
AttributeManager
    ATTR_TABLE = SET_TO Persons = FME_CONDITIONAL:DEFAULT_VALUE'_FME_NO_OP_'BOOL_OP;OR;COMPOSITE_TEST;<Unused>;CASE_INSENSITIVE_TEST @Value(ZoneName) BEGINS_WITH RS'2'BOOL_OP;OR;COMPOSITE_TEST;<Unused>;CASE_INSENSITIVE_TEST @Value(ZoneName) BEGINS_WITH RT'4'BOOL_OP;OR;COMPOSITE_TEST;<Unused>;CASE_INSENSITIVE_TEST @Value(ZoneName) BEGINS_WITH RM'12'BOOL_OP;OR;COMPOSITE_TEST;<Unused>;CASE_INSENSITIVE_TEST @Value(ZoneName) BEGINS_WITH CD'8'BOOL_OP;OR;COMPOSITE_TEST;<Unused>;CASE_INSENSITIVE_TEST @Value(ZoneName) BEGINS_WITH C'1'FME_NUM_CONDITIONS6___
    -> Cloner
Cloner
    COPIES = @Value(Persons)
    COPYATT = _copynum
    COPY -> StatisticsCalculator
    <REJECTED> -> Junction
Junction

Bookmark: Divide Residents
StatisticsCalculator
    COMPUTE_HISTOGRAM = NO
    COUNT_ATTR = TotalResidents
    PREPEND_ATTR_NAME_CHOICE = For multiple results only
    STATS_ATTRS = COUNTRY
    COMPLETE -> ExpressionEvaluator
ExpressionEvaluator
    ACTION = Create New Attribute
    EXPRESSION = @ceil((@Value(TotalResidents)/5))
    VAL_ATTR = GroupSize
    -> SpatialSorter
SpatialSorter
    OutputBounds = No
    OutputCurve = No
    OutputGroup = @Value(GroupSize)
    SortPrecision = 255
    Sorted -> Aggregator
    Sorted -> PointOnAreaOverlayer_2 [POINT]

Bookmark: Group Residents
Aggregator
    ACCUM_ATTRS_NAME = Use Attributes From One Feature
    AGGREGATE_TYPE = Homogeneous Collection (If Possible)
    GROUP_BY = GroupID
    MODE = Geometry - Assemble One Level
    ORDERED = No
    SEP = ,
    AGGREGATE -> HullReplacer

Bookmark: Create Boundaries
HullReplacer
    3DMODE_PARAM = Automatic
    HULLTYPE_PARAM = Convex ()
    HULL -> AreaOnAreaOverlayer [AREA]

Bookmark: Clean Up Overlaps
AreaOnAreaOverlayer
    ACCUM_ATTRS_NAME = Drop Incoming Attributes
    CLEANING_TOLERANCE = None
    CONNECT_Z_MODE = First Wins
    DEAGGREGATE_INPUT = Yes
    OVC_ATTR = _overlaps
    AREA -> PointOnAreaOverlayer_2 [AREA]
PointOnAreaOverlayer_2
    ATTR_ACCUM_MODE = Merge Incoming
    ATTR_CONFLICT_RES = Use Original
    CANDIDATE_LIST_ATTRS_TO_INCLUDE = GroupID
    CANDIDATE_LIST_ATTRS_TO_INCLUDE_MODE = Selected Attributes
    CANDIDATE_LIST_NAME = PointList
    DEAGGREGATE_INPUT = Yes
    OV_ATTR = _overlaps
    POLYS_FIRST = NO
    AREA -> ListHistogrammer
ListHistogrammer
    LIST_NAME = _histogram
    SRC_LIST = PointList{}.GroupID
    -> Dissolver
Dissolver
    ACCUM_INPUT_ATTRS = Use Attributes From One Feature
    CLEANING_TOLERANCE = None
    CONNECT_Z_MODE = First Wins
    DEAGGREGATE_INPUT = Yes
    GROUP_BY = _histogram{0}.value
    NO_OVRLP = No
    AREA -> GarbageZones (writer GEOPACKAGE_1)

Bookmark: Zones
GarbageZones (writer GEOPACKAGE_1)

Bookmark: Write Data as Points
FeatureWriter
    DATASET = C:\FMEData2018\Output
    DATASET_ATTR = _dataset
    ESRISHAPE_COMPRESSED_SHAPE_FILE = No
    ESRISHAPE_DESTINATION_DATASETTYPE_VALIDATION = Yes
    ESRISHAPE_DIMENSION = auto
    ESRISHAPE_ENCODING = SYSTEM
    ESRISHAPE_MEASURES_AS_Z = no
    ESRISHAPE_PRESERVE_RING_VERTEX_ORDER = No
    ESRISHAPE_STRICT_COMPATIBILITY = Yes
    ESRISHAPE_SURFACE_AND_SOLID_STORAGE = shape_multipatch
    ESRISHAPE_UPPER_CASE_ATTR_NAMES = No
    ESRISHAPE_WRITE_SPATIAL_INDEX = No
    FEATURE_TYPE_LIST_ATTR = _feature_type
    FORMAT = ESRISHAPE
    TOTAL_FEATURES_WRITTEN_ATTR = _total_features_written

Bookmark: Documentation
Note: This workspace creates new boundaries for garbage collection areas for the city of Vancouver, dividing the city into five areas with approximately equal numbers of residents.
Note: This workspace requires FME 2018.0 (build 18266 or greater)
Note: The workspace reads zoning data (MapInfo TAB) and an address database (Geodatabase). It outputs new garbage collection areas in GeoPackage format.
Note: This workspace makes use of the SpatialSorter transformer from the FME Hub (hub.safe.com)

FME custom transformer SpatialSorter
Sorts data on a spatial basis. The closer features are spatially, the closer they will be ordered.
Methodology
The transformer generates a Hilbert Curve. This is a curve that fills a given space, taking such a path as to preserve a measure of locality between vertices. 
The curve is warped into the same space as the incoming spatial data, and the nearest vertex on the curve is calculated for each feature. Features are then sorted according to that vertex number.
If multiple features are related to a single vertex, then their order within that group is random (it may relate to the order of the input).
Parameters
The Sort Precision parameter allows the selection of different scales of curve. The higher the number, the more vertices exist on the curve; the more vertices on the curve, the fewer features assigned to it. Therefore a higher number produces a greater degree of precision to the sorting, at the cost of a slightly more intense computation.
Size must also relate to the type of data. For point features a higher number definitely produces better results. For polygon features it's important to pick a grid size such that each polygon does not contain too many of the curve's vertices; therefore a higher number is not always better.
The Output Hilbert Curve parameter determines whether the generated curve is to also be output. 
The Output Sorted Feature Boundaries determines whether a bounding box for each set of features (those related to the same curve vertex) is also to be output. The boundaries show which features are grouped in a set (they are equally spatially related).
Group Size is an optional parameter (x) that can be set to any integer greater than zero. When set each feature is given a group ID number, where the group size is x features. For example, when set to 100 the data is given an attribute that defines groups of 100 features. Because the data has been spatially sorted it means that each group should occupy its own space, with minimum overlap to other groups.
Output
The output is the same set of data as the input, but sorted so that the order represents a measure of locality.
Each feature is given a new attribute called HilbertOrder. This is the attribute created to sort the data. It can be used to create groups of spatially related features.
Uses
This transformer is very useful for sorting spatial data that is not in a known order. Reordering the data could make data loading faster, improve the performance of data analysis, or make possible the sort of analysis that requires the selection of a set of features known to be local to each other.
For example, if I have a number of addresses to be visited, I can group the addresses spatially and assign 100 to each team. By spatially sorting the addresses travel is minimized.
Hey, this uses advanced mathematics and Python scripts. I'm flying by the seat of my pants here. If you need more information then email me (mark.ireland@safe.com) and I'll do my best to help - but I guarantee nothing!
The workspace has been tested on mainly point features.
This workspace uses a Python script to generate the Hilbert array. I got the majority of it from this blog post and a lot of help from FME enthusiast Takashi.

Parameters:
- SortPrecision = 63   # Sort Precision (Grid Size)
- OutputCurve = No   # Output Hilbert Curve
- OutputBounds = No   # Output Sorted Feature Boundaries
- OutputGroup =   # [Optional] Group Size

Input (input)
    -> CoordinateSystemExtractor
    -> Junction
CoordinateSystemExtractor
    CRDSYS_ATTR = _coordsys
    -> BoundingBoxAccumulator
    -> Junction_3
Note: CoordSys Info for Hilbert Grid
Junction_3
    -> Junction_4
Note: CoordSys Info
Junction_4
    -> Sampler
Note: Only needs 1 feature
Sampler
    RATE = 1
    SAMPLE_MODE = No
    SAMPLE_TYPE_LONG = First N Features
    SAMPLED -> FeatureMerger_2 [SUPPLIER]
Note: Data to be sorted / (NeighborFinder)
Junction
    -> Junction_2
Note: Input
Junction_2
    -> NeighborFinder [BASE]
Note: Get Coord Sys Info
FeatureMerger_2
    ATTR_ACCUM_MODE = Merge Supplier
    ATTR_CONFLICT_RES = Use Requestor
    CLEANING_TOLERANCE = None
    IGNORE_NULLS = No
    JOIN_KEYS = 1 1 AUTO
    MERGE_TYPE = Attributes Only
    PROCESS_DUPS = No
    REJECT_NULL_MISSING_KEYS = No
    SUPPLIERS_FIRST = No
    MERGED -> CoordinateSystemSetter_2
Note: Tag data as having same coordinate system as the incoming features
CoordinateSystemSetter_2
    COORDSYS = @Value(_coordsys)
    -> AffineWarper [OBSERVED]
Note: Curve Points
Note: Warp Hilbert grid to overlay incoming data
AffineWarper
    CORRECTED -> AttributeKeeper
    CORRECTED -> Tester
AttributeKeeper
    KEEP_ATTRS = sub
    -> NeighborFinder [CANDIDATE]
Note: Find nearest hilbert grid point to each incoming feature
NeighborFinder
    ATTR_ACCUM_MODE = Merge Candidate
    ATTR_CONFLICT_RES = Use Base
    CANDIDATES_FIRST = No
    INSERT_VERTEX = No
    K = 1
    MEASURES_FROM_CANDIDATE = Yes
    MEASURE_TYPE = Continuous
    MODE = Bases and Candidates
    TREAT_POLYGON_AS = Lines
    MATCHED -> AttributeRemover
AttributeRemover
    REMOVE_ATTRS = _closest_candidate_x,_candidate_angle,_candidate_label_angle,_distance,_closest_candidate_y,_closest_base_x,_closest_base_y,_angle
    -> Sorter_3
Note: Sort incoming data according to hilbert grid point order
Sorter_3
    SORT_PARM = sub NUMERIC ASCENDING
    SORTED -> AttributeRenamer
    SORTED -> Tester_2
AttributeRenamer
    ATTR_TABLE = RENAME_SET_DEFAULT sub > HilbertOrder
    -> Tester_3
Note: Check if grouping required
Tester_3
    BOOL_OP = OR
    TEST_CLAUSE = TEST $(OutputGroup) > 0
    PASSED -> Counter_3
    FAILED -> Sorted (output)
Sorted (output)

Bookmark: Get extents of incoming data. Create vectors to warp hilbert grid into position
BoundingBoxAccumulator
    ACCUM_ATTRS_NAME = Use Attributes From One Feature
    TOPFER_INDEX = No
    BOUNDING_BOX -> BoundsExtractor
BoundsExtractor
    XMAX = _xmax
    XMIN = _xmin
    YMAX = _ymax
    YMIN = _ymin
    ZMAX = _zmax
    ZMIN = _zmin
    -> GeometryRemover
GeometryRemover
    -> VertexCreator_2
    -> VertexCreator_4
    -> VertexCreator_6
    -> VertexCreator_8
VertexCreator_2
    MODE_NAME = Add Point
    XVAL = 0
    YVAL = $(SortPrecision)*-100
    -> VertexCreator
VertexCreator
    MODE_NAME = Add Point
    XVAL = @Value(_xmin)
    YVAL = @Value(_ymin)
    -> AffineWarper [CONTROL]
VertexCreator_4
    MODE_NAME = Add Point
    XVAL = $(SortPrecision)*100
    YVAL = 0
    -> VertexCreator_3
VertexCreator_3
    MODE_NAME = Add Point
    XVAL = @Value(_xmax)
    YVAL = @Value(_ymax)
    -> AffineWarper [CONTROL]
VertexCreator_6
    MODE_NAME = Add Point
    XVAL = $(SortPrecision)*100
    YVAL = $(SortPrecision)*-100
    -> VertexCreator_5
VertexCreator_5
    MODE_NAME = Add Point
    XVAL = @Value(_xmax)
    YVAL = @Value(_ymin)
    -> AffineWarper [CONTROL]
VertexCreator_8
    MODE_NAME = Add Point
    XVAL = 0
    YVAL = 0
    -> VertexCreator_7
VertexCreator_7
    MODE_NAME = Add Point
    XVAL = @Value(_xmin)
    YVAL = @Value(_ymax)
    -> AffineWarper [CONTROL]

Bookmark: Create Hilbert Curve Numbering Array
Creator
    GEOMTYPE = Geometry Object
    NUM = 1
    CREATED -> ParameterFetcher
ParameterFetcher
    ATTR_LIST = SortPrecision $(SortPrecision)
    -> AttributeManager
AttributeManager
    ATTR_TABLE = SET_TO SortPrecision = @Evaluate(@Value(SortPrecision)+1)
    -> PythonCaller_3
PythonCaller_3
    NEW_ATTRIBUTES = _list2{} _list2{}.sub{}
    PYTHONSOURCE:
      import fme
      import fmeobjects
      import numpy
      from numpy import *

      def hilbert_curve(n):
          ''' Generate Hilbert curve indexing for (n, n) array. 'n' must be a power of two. '''
          # recursion base
          if n == 1:
              return numpy.zeros((1, 1), int32)
          # make (n/2, n/2) index
          t = hilbert_curve(n//2)
          # flip it four times and add index offsets
          a = flipud(rot90(t))
          b = t + t.size
          c = t + t.size*2
          d = flipud(rot90(t, -1)) + t.size*3
          # and stack four tiles into resulting array
          return vstack(map(hstack, [[a, b], [d, c]]))

      def processFeature(feature):
          curvenum = feature.getAttribute('SortPrecision')
          for i, s in enumerate(hilbert_curve(curvenum)):
              for j, v in enumerate(s):
                  feature.setAttribute('_list2{%d}.sub{%d}' % (i, j), int(v))
          pass
    PYTHONSYMBOL = processFeature
    -> ListExploder
ListExploder
    ATTR_ACCUM_MODE = Merge Incoming List
    ATTR_CONFLICT_RES = Use Incoming List
    INDEX_ATTR = _element_index
    LIST_ATTR = _list2{}
    ELEMENTS -> ListExploder_2
ListExploder_2
    ATTR_ACCUM_MODE = Merge Incoming List
    ATTR_CONFLICT_RES = Use Incoming List
    INDEX_ATTR = _element_index
    LIST_ATTR = sub{}
    ELEMENTS -> Counter_2

Bookmark: Match Hilbert Numbering to Hilbert Points
Counter_2
    CNT_ATTR = _count
    DOMAIN = counter1
    SCOPE = Global
    START = 0
    -> FeatureMerger [SUPPLIER]
Counter
    CNT_ATTR = _count
    DOMAIN = counter2
    SCOPE = Global
    START = 0
    -> FeatureMerger [REQUESTOR]
FeatureMerger
    ATTR_ACCUM_MODE = Merge Supplier
    ATTR_CONFLICT_RES = Use Requestor
    IGNORE_NULLS = No
    JOIN_KEYS = @Value(_count) @Value(_count) AUTO
    MERGE_TYPE = Attributes Only
    PROCESS_DUPS = No
    REJECT_NULL_MISSING_KEYS = No
    SUPPLIERS_FIRST = No
    MERGED -> FeatureMerger_2 [REQUESTOR]

Bookmark: Create Hilbert Curve Points Array
2DGridCreator
    COL_ATTR = _column
    GRID_TYPE = Points (Corners)
    NUMCOLS = $(SortPrecision)
    NUMROWS = $(SortPrecision)
    ROW_ATTR = _row
    STARTINGCORNER = Upper Left
    STARTINGX = 0
    STARTINGY = 0
    XINC = 100
    YINC = 100
    CREATED -> Sorter
Sorter
    SORT_PARM = _row NUMERIC ASCENDING _column NUMERIC ASCENDING
    SORTED -> Counter

Bookmark: Create Group IDs
Counter_3
    CNT_ATTR = _SpatialSortCounter
    DOMAIN = SpatialSortCounter
    SCOPE = Global
    START = 1
    -> ModuloCounter
ModuloCounter
    CNT_ATTR = _SpatialSortModulo
    DOMAIN = SpatialSortModulo
    MOD = $(OutputGroup)
    -> ExpressionEvaluator
ExpressionEvaluator
    ACTION = Create New Attribute
    EXPRESSION = @Value(_SpatialSortCounter)-@Value(_SpatialSortModulo)
    VAL_ATTR = _SpatialSortGroup
    -> Aggregator
    -> FeatureMerger_3 [REQUESTOR]
Aggregator
    ACCUM_ATTRS_NAME = Use Attributes From One Feature
    AGGREGATE_TYPE = Homogeneous Collection (If Possible)
    GROUP_BY = _SpatialSortGroup
    MODE = Geometry - Assemble One Level
    ORDERED = No
    SEP = ,
    AGGREGATE -> Counter_4
Counter_4
    CNT_ATTR = GroupID
    DOMAIN = SpatialSortFinalGroupCounter
    SCOPE = Global
    START = 1
    -> FeatureMerger_3 [SUPPLIER]
FeatureMerger_3
    ATTR_ACCUM_MODE = Merge Supplier
    ATTR_CONFLICT_RES = Use Requestor
    CLEANING_TOLERANCE = None
    IGNORE_NULLS = No
    JOIN_KEYS = @Value(_SpatialSortGroup) @Value(_SpatialSortGroup) AUTO
    MERGE_TYPE = Attributes Only
    PROCESS_DUPS = No
    REJECT_NULL_MISSING_KEYS = No
    SUPPLIERS_FIRST = No
    MERGED -> Sorted (output)

Bookmark: Create Sorted Area Bounds
Tester_2
    BOOL_OP = OR
    TEST_CLAUSE = TEST $(OutputBounds) = Yes
    PASSED -> FeatureColorSetter
FeatureColorSetter
    MODE = Random
    RANDOM_MODE = Attributes
    COLORED -> BoundingBoxAccumulator_2
BoundingBoxAccumulator_2
    ACCUM_ATTRS_NAME = Use Attributes From One Feature
    GROUP_BY = sub
    TOPFER_INDEX = No
    BOUNDING_BOX -> HilbertGroups (output)
HilbertGroups (output)

Bookmark: Create Hilbert Curve
Tester
    BOOL_OP = OR
    TEST_CLAUSE = TEST $(OutputCurve) = Yes
    PASSED -> Sorter_2
Sorter_2
    SORT_PARM = sub NUMERIC ASCENDING
    SORTED -> PointConnector
PointConnector
    ACCUM_INPUT_ATTRS = Drop Incoming Attributes
    LINE -> HilbertCurve (output)
HilbertCurve (output)
