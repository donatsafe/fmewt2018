FME workspace MyWorkspaceForServer.fmw

Parameters:
- SourceDataset_OGCKML = $(FME_MF_DIR)VancouverNeighborhoods.kml   # Source Google KML File or URL
- SourceDataset_GML = $(FME_MF_DIR)ElectionVoting.gml   # Source Geography Markup Language (GML) File(s)
- DestDataset_OGCKML = /Users/lwu/Dropbox (Safe Software Inc.)/MyFiles/Demos/WT2018_FMEServer/myoutputkml.kml   # Destination Google KML File

Readers:
- OGCKML_1: OGCKML from $(SourceDataset_OGCKML)
- GML_1: GML from $(SourceDataset_GML)

Writers:
- OGCKML_2: OGCKML to $(DestDataset_OGCKML)

VotingPlaces (reader GML_1)
    attributes: Division xml_char(3), Name xml_char(50), Number xml_char(4), Street xml_char(20), Room xml_char(30), gml_pointProperty xml_geometry, gml_multiPointProperty xml_geometry
    -> Clipper [CLIPPEE]
Neighborhoods (reader OGCKML_1)
    attributes: NeighborhoodId kml_buffer, NeighborhoodName kml_buffer, NeighborhoodURL kml_buffer, TotalPopulation2001 kml_buffer, TotalPopulation2011 kml_buffer
    -> Reprojector
Reprojector
    DEST = UTM83-10
    INTERPOLATION_TYPE_NAME = Nearest Neighbor
    RASTER_CELL_SIZE = Preserve Cells
    RASTER_TOLERANCE = 0.0
    SOURCE = Read from feature
    REPROJECTED -> Clipper [CLIPPER]
    REPROJECTED -> Neighborhoods (writer OGCKML_2)
Clipper
    ATTR_ACCUM_MODE = Merge Clipper
    ATTR_CONFLICT_RES = Use Clippee
    BOUNDARY_CASES = Treat as Inside
    CLEANING_TOLERANCE = None
    CLIPPED_ATTR = _clipped
    CLIP_TYPE = Multiple Clippers
    CREATE_AGGREGATES = Yes
    LINES_AS_SEGMENTS = No
    MEASURE_TYPE = Continuous
    MISSING_VAL_MODE = Compute
    PRESERVE_CLIPPEE_EXTENTS = No
    VAL_SOURCE = Clippee Only
    INSIDE -> VotingPlaces (writer OGCKML_2)
VotingPlaces (writer OGCKML_2)
    attributes: gml_id kml_char(255), gml_parent_id kml_char(255), gml_parent_property kml_char(255), Division kml_char(3), Name kml_char(50), Number kml_char(4), Street kml_char(20), Room kml_char(30), gml_pointProperty kml_char(255), gml_multiPointProperty kml_char(255)
Neighborhoods (writer OGCKML_2)
    attributes: NeighborhoodId kml_char(255), NeighborhoodName kml_char(255), NeighborhoodURL kml_char(255), TotalPopulation2001 kml_char(255), TotalPopulation2011 kml_char(255)
