FME workspace AffordabilityComplete.fmw

Parameters:
- CITY = Portland
- SourceDataset_CSV2 = /Users/dmurray/Dropbox (Safe Software Inc.)/DonStuffMac/DonStuff/DemoData/FME2018/FMEWT2018Stuff/IntroDemo/source/USCensusByNeighbourhood.csv   # Source CSV (Comma Separated Value) File(s)
- DestDataset_POWERPOINT = $(FME_MF_DIR_USERTYPED)presentation.pptx   # Destination Microsoft PowerPoint file
- DestDataset_OGCKML = $(FME_MF_DIR_USERTYPED)KML   # Destination Google KML File
- DestDataset_FME_AR = $(FME_MF_DIR_USERTYPED)FMEAR   # Destination FME AR Folder
- POWERPOINT_OUT_TEMPLATE_DOC_POWERPOINT_2 = $(FME_MF_DIR_USERTYPED)source/powerpoint_template.pptx   # Template Microsoft PowerPoint file

Readers:
- CSV2_1: CSV2 from $(SourceDataset_CSV2)

Writers:
- POWERPOINT_1: POWERPOINT to $(DestDataset_POWERPOINT)
- OGCKML_1: OGCKML to $(DestDataset_OGCKML)
- FME_AR_1: FME_AR to $(DestDataset_FME_AR)

FeatureJoiner
    ATTR_CONFLICT_RES = Use Left
    GEOMETRY_HANDLING = Use Left
    JOIN_KEYS = RegionID RegionID AUTO
    JOIN_MODE = Inner
    JOINED -> Sorter
    JOINED -> GradedColorizer

Bookmark: Zillow City Neighborhoods
SQLCreator
    DATASET = /Users/dmurray/Dropbox (Safe Software Inc.)/DonStuffMac/DonStuff/DemoData/FME2018/FMEWT2018Stuff/IntroDemo/source/ZillowNeighbourhoods.gpkg
    EXPOSED_ATTRIBUTE_LIST = Name,City,County,RegionID,State
    FORMAT = GEOPACKAGE
    GEOPACKAGE_ENCODE_FEATURE_TYPE_AND_ATTR_NAMES = YES
    GEOPACKAGE_ENFORCE_FOREIGN_KEY_INTEGRITY = YES
    GEOPACKAGE_OPEN_SINGLE_RASTER_AS_SUBDATASET = YES
    GEOPACKAGE_QUERY_FEATURE_TYPES_FOR_MERGE_FILTERS = Yes
    GEOPACKAGE_READ_BOOLEANS_AS_YES_NO = YES
    GEOPACKAGE_READ_NULLS = YES
    SQL_STATEMENT:
      SELECT * FROM "neighbourhoods"
      WHERE city = '$(CITY)'
    RESULT -> FeatureJoiner [LEFT]

Bookmark: US Census Data
CSV (reader CSV2_1)
    attributes: RegionID string, City string, Name string, State string, City Min Property Value string, City Max Property Value string, Averaged Median Property Value string, City Min Household Income string, City Max Household Income string, Averaged Median Household Income string, Property To Income Ratio string, Normalized Ratio string
    -> FeatureJoiner [RIGHT]

Bookmark: Heat Map
GradedColorizer
    Attribute_to_Color = @Value(Property To Income Ratio)
    Binning_Method = C
    Color_Scheme = 8
    Number_of_Bands = 10
    -> PowerPointStyler_Map
    -> KMLStyler
    -> Deaggregator

Bookmark: Extrude & Style For AR
Deaggregator
    ATTR_ACCUM_MODE = Merge List Attributes
    ATTR_CONFLICT_RES = Use List Attribute Values
    CHILD_ID_ATTR = _hierarchy_child_id_list
    COPY_ATTR = Every Node
    EXPLODE_INSTANCES = No
    GEOM_NAME_FIELD = _geometry_name
    ID_ATTR = _hierarchy_id
    ID_SELECTION = ID and Parent ID
    LIST_ATTR_MODE_LOOKUP = LEAN
    MODE = Flatten One Level
    PARENT_ID_ATTR = _hierarchy_parent_id
    PART_NUMBER_FIELD = _part_number
    SPLIT_COMPOSITES = No
    DEAGGREGATED -> Extruder
Extruder
    DIRECTION = Vertical
    DISTANCE = @Value(Property To Income Ratio)*4000
    EXTRUDED -> AppearanceSetter [GEOMETRY]
    EXTRUDED -> AppearanceStyler
AppearanceStyler
    ALPHA = 1.0
    APPEARANCE_NAME = affordability
    DIFFUSE_COLOR = @Value(fme_fill_color)
    SHININESS = .1
    SPECULAR_COLOR = 0.78584,0.78584,0.78584
    TEXTURE_CENTER_U = 0.0
    TEXTURE_CENTER_V = 0.0
    TEXTURE_ROTATION_ANGLE = 0.0
    TEXTURE_U_OFFSET = 0.0
    TEXTURE_U_SCALING_FACTOR = 1.0
    TEXTURE_U_SHEARING_FACTOR = 0.0
    TEXTURE_V_OFFSET = 0.0
    TEXTURE_V_SCALING_FACTOR = 1.0
    TEXTURE_V_SHEARING_FACTOR = 0.0
    TEXTURE_WRAP_DISPLAY = Repeat in U and V
    -> AppearanceSetter [APPEARANCE]
AppearanceSetter
    APPEARANCE_NAME = affordability
    DEF_STORAGE = Create New Definitions
    GQUERY:
      for $geom in //geometry
      where $geom/count(parent::geometry) = 0
      return number($geom/@fme_id)
    GROUP_BY = fme_fill_color
    SET_ON_SIDE = Front and Back Sides
    TEXTURE_MAPPING_TYPE_CHOICE = Surface Normal
    TEXTURE_U_OFFSET2 = 0.0
    TEXTURE_U_SCALE_FACTOR = 1.0
    TEXTURE_V_OFFSET2 = 0.0
    TEXTURE_V_SCALE_FACTOR = 1.0
    USE_EXISTING_TEXTURE_COORDINATES = No
    -> Asset1 (writer FME_AR_1)

Bookmark: AR
Asset1 (writer FME_AR_1)

Bookmark: KML
KMLStyler
    COLOR = @Value(fme_color)
    FILL_COLOR = @Value(fme_fill_color)
    FILL_OPACITY = 0.4
    ICON_OPACITY = 1.0
    ICON_SCALE = 0.8
    LABEL_OPACITY = 1.0
    LABEL_SCALE = 1.0
    LABEL_VISIBILITY = Yes
    LINE_WIDTH = 1.0
    LINE_WIDTH_UNITS = Pixels (Display Units)
    OPACITY = 1.0
    STYLE_PER_FEATURE = Yes
    KMLStyled -> AttributeManager
AttributeManager
    ATTR_TABLE:
      SET_TO fme_feature_type = 2D
      RENAME_SET_VALUE Property To Income Ratio > ratio
    -> 3d (writer OGCKML_1)
3d (writer OGCKML_1)
    attributes: City kml_char(255), County kml_char(200), Name kml_char(255), RegionID kml_char(255), State kml_char(255), _stdevp kml_char(200), City Min Property Value kml_char(255), City Max Property Value kml_char(255), Averaged Median Property Value kml_char(255), City Min Household Income kml_char(255), City Max Household Income kml_char(255), Averaged Median Household Income kml_char(255), ratio kml_char(200), Normalized Ratio kml_char(255)

Bookmark: PowerPoint Presentation
PowerPointStyler_Map
    PARAMETER_SETUP = pptx_slide_subtype[WithTitle[pptx_title_text[@Value(City) Affordability Heatmap (Red=$$$)[pptx_caption_text[<Unused>[LABEL_GROUP[FME_DISCLOSURE_CLOSED[pptx_map_label[[fme_pptx_font_data[[pptx_font_color[[pptx_label_wrap[No[FILL_GROUP[FME_DISCLOSURE_OPEN[pptx_map_fill_pattern[[pptx_map_fill_fore_color[@Value(fme_color)[pptx_map_fill_back_color[[BORDER_GROUP[[pptx_map_border_style[[pptx_map_border_width[1[pptx_map_border_color[0,0,0[HYPERLINK_GROUP[[pptx_map_hyperlink[[pptx_merge_features[Yes[pptx_merge_id[a[FME_CONTROLLER_QUERY_FILE[transformers/dependencies/powerpoint/slide_types/Map Slide.fme
    SLIDE_TYPE = Map Slide
    pptx_slide_order = 0
    -> presentation (writer POWERPOINT_1)
PowerPointStyler_Table
    PARAMETER_SETUP = pptx_title_text[Top 5 Most Unaffordable[pptx_table_style["Medium Style 2 Accent 1"[pptx_table_banding[Yes[pptx_measurement_units[Inches[fme_pptx_table_data[Neighborhood}_mostExpensive{}.Name}Stretch}Land Value}_mostExpensive{}.Averaged Median Property Value}Stretch}Average Income}_mostExpensive{}.Averaged Median Household Income}Stretch[FME_CONTROLLER_QUERY_FILE[transformers/dependencies/powerpoint/slide_types/Table Slide.fme
    SLIDE_TYPE = Table Slide
    pptx_slide_order = 1
    -> presentation (writer POWERPOINT_1)
presentation (writer POWERPOINT_1)

Bookmark: Affordability Table
Sorter
    SORT_PARM = "Property To Income Ratio" NUMERIC DESCENDING
    SORTED -> Sampler
Sampler
    RATE = 5
    SAMPLE_MODE = No
    SAMPLE_TYPE_LONG = First N Features
    SAMPLED -> DollarFormatter
DollarFormatter
    ATTRS = "Averaged Median Household Income","Averaged Median Property Value"
    -> ListBuilder
ListBuilder
    GROUPS_ORDERED = No
    LIST_ATTRS_TO_INCLUDE = Name Averaged Median Household Income Averaged Median Property Value
    LIST_NAME = _mostExpensive
    -> PowerPointStyler_Table

FME custom transformer DollarFormatter
Formats numeric values into a $xxx,yyy.zz string, suitable for reports to be consumed by humans.
Note that this will not work on attributes whose names contain " or , characters.

Parameters:
- ATTRLIST_COMMAS =   # ATTRS " " Attributes To Format

Input (input)
    -> ParameterFetcher
ParameterFetcher
    ATTR_LIST = _ATTRS $(ATTRS)
    -> AttributeEncoder
Note: Convert attributes to utf-8
AttributeEncoder
    ATTRCHOICE = Selected Attributes
    ATTRLIST = _ATTRS
    DEST_ENCODING = utf-8
    TREAT_AS_BYTES = Honor Encoding
    -> PythonCaller
PythonCaller
    PYTHONSOURCE:
      import fme

      import fmeobjects

      # Format two attribute nicely as currency

      def FeatureProcessor(feature):

          attrsParm = feature.getAttribute('_ATTRS')

          # Note -- this technique does not work if the attr names had " or , in them

          listOfAttrs = [x.strip('"') for x in attrsParm.split(',')]

          for attr in listOfAttrs:

              value = float(feature.getAttribute(attr)) or ''
              try:
                  value_str = "${:,.2f}".format(value)
              except ValueError, TypeError:
                  value_str = value
              feature.setAttribute(attr, value_str)
    PYTHONSYMBOL = FeatureProcessor
    -> Output (output)
Output (output)

FME custom transformer GradedColorizer
Colors features along a delineated range of colors based on the values of a numerical attribute.
This transformer has five parameters:
    Attribute to Classify on: Here you select a numerical attribute which the feature colors will be based on
    Color Scheme: Here you select the color gradient you wish the features to follow
    Classification Method: Here you select the method used to classify the features, four options are available:
    Set Intervals- in this option intervals are determined by user entered numerical values in the Interval Break Values Parameter
    Equal Intervals- creates a user specified number of intervals of equal length based on the range of the numerical attribute
    Quantile- creates a user specified number of intervals where features are uniformly distributed over intervals 
    Unique Values- Each group will contain features with the same classification attribute value
    Number of Intervals: Here you specify the number of intervals (Ignored if Classification method is set intervals or Unique Values)
    Interval Break Values: Here you enter the interval break points as a space delimited string (Ignored if Classification method is not set intervals) Eg. '0 10 20 30 40'

Parameters:
- Attribute_to_Color =   # Attribute to Color on
- Color_Scheme = 1   # Rainbow,2%Red to White,3%White to Red,4%Blue to White,5%White to Blue,6%Red to Green,7%Green to Red,8 Color Scheme
- Binning_Method = B   # Set Intervals,A%Equal Intervals,B%Quantile,C%Unique Values,D Classification Method
- Number_of_Bands = 4   # Number of Intervals
- RangeVals =   # Interval Break Values

INPUT (input)
    -> ParameterFetcher_2
AttributeRemover
    REMOVE_ATTRS = GC_min,_part_number,GC_count,_geometry_name,GC_Color_Scheme,GC_RangeVals,GC_Value,rval,GC_Binning_Method,GC_tcount,GC_Number_of_Bands,GC_range
    -> OUTPUT (output)
OUTPUT (output)

Bookmark: Pull Parameters into Attributes
ParameterFetcher_2
    ATTR_LIST = GC_Number_of_Bands {$(Number_of_Bands)} GC_Color_Scheme {$(Color_Scheme)} GC_RangeVals {$(RangeVals)} GC_Value {$(Attribute_to_Color)} GC_Binning_Method {$(Binning_Method)}
    -> TestFilter

Bookmark: Branch based on Classification Method
TestFilter
    DEFAULT_VALUE = <UNFILTERED>
    TEST_LIST = BOOL_OP,OR,COMPOSITE_TEST,<Unused>,TEST_CLAUSE,"TEST @Value(GC_Binning_Method) = A",Binning_Method = A,BOOL_OP,OR,COMPOSITE_TEST,<Unused>,TEST_CLAUSE,"TEST @Value(GC_Binning_Method) = B",Binning_Method = B,BOOL_OP,OR,COMPOSITE_TEST,<Unused>,TEST_CLAUSE,"TEST @Value(GC_Binning_Method) = C",Binning_Method = C,BOOL_OP,OR,COMPOSITE_TEST,<Unused>,TEST_CLAUSE,"TEST @Value(GC_Binning_Method) = D",Binning_Method = D
    Binning_Method = A -> PythonCaller_4
    Binning_Method = B -> StatisticsCalculator
    Binning_Method = C -> StatisticsCalculator_2
    Binning_Method = D -> Aggregator

Bookmark: Calculate RGB based on specified Intervals
PythonCaller_4
    PYTHONSOURCE:
      import fmeobjects, math, colorsys
      # Template Function interface:
      def processFeature(feature):
         pass

      # Template Class Interface:
      class FeatureProcessor(object):
         def __init__(self):
             pass
         def input(self,feature):

             # Get interval break values
             rval=feature.getAttribute("GC_RangeVals")

             # Number of groups = number of break values plus 1
             bands=len(rval.split())+1;

             # Get color scheme and attribute to color on, also initialize variables
             Value=float(feature.getAttribute("GC_Value"))
             cs=int(feature.getAttribute("GC_Color_Scheme"))
             R=0.0
             G=0.0
             B=0.0
             global bin
             i=0

             # for each value in the input list of break values
             for val in rval.split():

                 # Check if the attribute value is less than or equal to the break value used in this iteration
                 if Value<=float(val):
                     # Set the feature's color
                     [R,G,B]=self.color(i,cs,bands)
                     feature.setAttribute("fme_color",str(R)+","+str(G)+","+str(B))
                     feature.setAttribute("fme_fill_color",str(R)+","+str(G)+","+str(B))
                     break
                 # If the attribute value is greater than the last break value, then it should be in the last group
                 elif Value>float(rval.split()[-1]):
                     # Set the feature's color
                     [R,G,B]=self.color(bands,cs,bands+1)
                     feature.setAttribute("fme_color",str(R)+","+str(G)+","+str(B))
                     feature.setAttribute("fme_fill_color",str(R)+","+str(G)+","+str(B))
                     break
                 # if we have reached here, the attribute value has not been less than or equal to the current break value and
                 # has not been greater than the last break value. It does not belong to group i, so it might belong to group i+1
                 i=i+1
             self.pyoutput(feature)
         def close(self):
             pass

         # This function sets feature's color based on the group it belongs to, the number of groups, and color scheme
         def color(self,i,cs,bands):
                     if (bands!=1):
                          bands-=1
                     if cs==1:
                          [R,G,B]=colorsys.hsv_to_rgb(float(i)/bands,1,1)
                     elif cs==2:
                          [R,G,B]=colorsys.hsv_to_rgb(1-float(i)/bands,1,1)
                     elif cs==3:
                          [R,G,B]=[1,float(i)/bands,float(i)/bands]
                     elif cs==4:
                          [R,G,B]=[1,1-float(i)/bands,1-float(i)/bands]
                     elif cs==5:
                          [R,G,B]=[float(i)/bands,float(i)/bands,1]
                     elif cs==6:
                          [R,G,B]=[1-float(i)/bands,1-float(i)/bands,1]
                     elif cs==7:
                          [R,G,B]=colorsys.hsv_to_rgb(float(i)/bands/3,1,1)
                     elif cs==8:
                          [R,G,B]=colorsys.hsv_to_rgb(1.0/3-float(i)/bands/3,1,1)
                     else:
                         [R,G,B]=[0,0,0]
                     return [R,G,B]
    PYTHONSYMBOL = FeatureProcessor
    -> AttributeRemover

Bookmark: Calculate RGB based on Equal Intervals
Note: Find minimum and range / of attribute values
StatisticsCalculator
    COMPUTE_HISTOGRAM = NO
    MIN_ATTR = GC_min
    PREPEND_ATTR_NAME_CHOICE = For multiple results only
    RANGE_ATTR = GC_range
    STATS_ATTRS = GC_Value
    STDEVP_ATTR = _stdevp
    COMPLETE -> PythonCaller_2
PythonCaller_2
    PYTHONSOURCE:
      import fmeobjects, math, colorsys
      # Template Function interface:
      def processFeature(feature):
         pass

      # Template Class Interface:
      class FeatureProcessor(object):
         def __init__(self):
             pass
         def input(self,feature):

             # Get all needed attributes and initialize variables
             bands=int(feature.getAttribute("GC_Number_of_Bands"))
             min=float(feature.getAttribute("GC_min"))
             valrange=float(feature.getAttribute("GC_range"))
             Value=float(feature.getAttribute("GC_Value"))
             cs=int(feature.getAttribute("GC_Color_Scheme"))
             R=0.0
             G=0.0
             B=0.0
             global bin

             # Check attribute value to determine which interval it falls into. Then assign color accordingly
             for i in range(bands):
                 if Value<=min+float(i+1)*float(valrange)/bands:
                     [R,G,B]=self.color(i,cs,bands)
                     feature.setAttribute("fme_color",str(R)+","+str(G)+","+str(B))
                     feature.setAttribute("fme_fill_color",str(R)+","+str(G)+","+str(B))
                     break

             self.pyoutput(feature)
         def close(self):
             pass

         # This function sets feature's color based on the group it belongs to, the number of groups, and color scheme
         def color(self,i,cs,bands):
                     if (bands!=1):
                          bands-=1
                     if cs==1:
                          [R,G,B]=colorsys.hsv_to_rgb(float(i)/bands,1,1)
                     elif cs==2:
                          [R,G,B]=colorsys.hsv_to_rgb(1-float(i)/bands,1,1)
                     elif cs==3:
                          [R,G,B]=[1,float(i)/bands,float(i)/bands]
                     elif cs==4:
                          [R,G,B]=[1,1-float(i)/bands,1-float(i)/bands]
                     elif cs==5:
                          [R,G,B]=[float(i)/bands,float(i)/bands,1]
                     elif cs==6:
                          [R,G,B]=[1-float(i)/bands,1-float(i)/bands,1]
                     elif cs==7:
                          [R,G,B]=colorsys.hsv_to_rgb(float(i)/bands/3,1,1)
                     elif cs==8:
                          [R,G,B]=colorsys.hsv_to_rgb(1.0/3-float(i)/bands/3,1,1)
                     else:
                         [R,G,B]=[0,0,0]
                     return [R,G,B]
    PYTHONSYMBOL = FeatureProcessor
    -> AttributeRemover

Bookmark: Calculate RGB based on Quantile
Note: Count the number / of input features
StatisticsCalculator_2
    COMPUTE_HISTOGRAM = NO
    COUNT_ATTR = GC_tcount
    PREPEND_ATTR_NAME_CHOICE = For multiple results only
    STATS_ATTRS = GC_Value
    STDEVP_ATTR = _stdevp
    COMPLETE -> Sorter
Note: Sort features by their / attribute value
Sorter
    SORT_PARM = GC_Value NUMERIC ASCENDING
    SORTED -> Counter
Note: Put IDs on features / ID for first =0 / ID for last = total count-1
Counter
    CNT_ATTR = GC_count
    DOMAIN = counter
    SCOPE = Global
    START = 0
    -> PythonCaller_3
PythonCaller_3
    PYTHONSOURCE:
      import fmeobjects, math, colorsys
      # Template Function interface:
      def processFeature(feature):
         pass

      # Template Class Interface:
      class FeatureProcessor(object):
         def __init__(self):
             global bin
             bin=0
             global preval
             preval=0
             pass
         def input(self,feature):

             # Get all needed attributes and initialize variables
             bands=int(feature.getAttribute("GC_Number_of_Bands"))
             Value=float(feature.getAttribute("GC_Value"))
             count=int(feature.getAttribute("GC_count"))
             tcount=int(feature.getAttribute("GC_tcount"))
             cs=int(feature.getAttribute("GC_Color_Scheme"))
             R=0.0
             G=0.0
             B=0.0
             global bin

             # If feature ID is less than the current group number times number of items in each group,
             # the feature belongs to current group
             if count<(bin+1)*tcount/bands:
                  [R,G,B]=self.color(bin,cs,bands)
             # If not, the feature belongs to the next group
             else:
                  [R,G,B]=self.color(bin+1,cs,bands)
                  bin=bin+1
             feature.setAttribute("fme_color",str(R)+","+str(G)+","+str(B))
             feature.setAttribute("fme_fill_color",str(R)+","+str(G)+","+str(B))
             self.pyoutput(feature)
         def close(self):
             pass

         # This function sets feature's color based on the group it belongs to, the number of groups, and color scheme
         def color(self,i,cs,bands):
                     if (bands!=1):
                          bands-=1
                     if cs==1:
                          [R,G,B]=colorsys.hsv_to_rgb(float(i)/bands,1,1)
                     elif cs==2:
                          [R,G,B]=colorsys.hsv_to_rgb(1-float(i)/bands,1,1)
                     elif cs==3:
                          [R,G,B]=[1,float(i)/bands,float(i)/bands]
                     elif cs==4:
                          [R,G,B]=[1,1-float(i)/bands,1-float(i)/bands]
                     elif cs==5:
                          [R,G,B]=[float(i)/bands,float(i)/bands,1]
                     elif cs==6:
                          [R,G,B]=[1-float(i)/bands,1-float(i)/bands,1]
                     elif cs==7:
                          [R,G,B]=colorsys.hsv_to_rgb(float(i)/bands/3,1,1)
                     elif cs==8:
                          [R,G,B]=colorsys.hsv_to_rgb(1.0/3-float(i)/bands/3,1,1)
                     else:
                         [R,G,B]=[0,0,0]
                     return [R,G,B]
    PYTHONSYMBOL = FeatureProcessor
    -> AttributeRemover

Bookmark: Group and sort based on unique values
Aggregator
    ACCUM_ATTRS_NAME = Yes
    AGGREGATE_TYPE = Homogeneous Collection (If Possible)
    GROUP_BY = GC_Value
    LIST_NAME = list
    MODE = Geometry - Assemble One Level
    ORDERED = No
    SEP = ,
    AGGREGATE -> Sorter_2
Sorter_2
    SORT_PARM = GC_Value NUMERIC ASCENDING
    SORTED -> Aggregator_2

Bookmark: Concatenate Unique Values and store in attribute
Aggregator_2
    ACCUM_ATTRS_NAME = Yes
    AGGREGATE_TYPE = Homogeneous Collection (If Possible)
    CONCAT_ATTRS = GC_Value
    LIST_NAME = list
    MODE = Geometry - Assemble One Level
    ORDERED = No
    SEP = " "
    AGGREGATE -> AttributeRenamer
AttributeRenamer
    ATTR_TABLE = RENAME_SET_DEFAULT GC_Value > rval = @Value(GC_Value)
    -> Deaggregator

Bookmark: Deaggregate to get features back
Deaggregator
    ATTR_ACCUM_MODE = Merge List Attributes
    ATTR_CONFLICT_RES = Use List Attribute Values
    EXPLODE_INSTANCES = No
    GEOM_NAME_FIELD = _geometry_name
    LIST_ATTR = list{}
    LIST_ATTR_MODE_LOOKUP = LEAN
    MODE = Flatten One Level
    PART_NUMBER_FIELD = _part_number
    SPLIT_COMPOSITES = No
    DEAGGREGATED -> Deaggregator_2
Deaggregator_2
    ATTR_ACCUM_MODE = Merge List Attributes
    ATTR_CONFLICT_RES = Use List Attribute Values
    EXPLODE_INSTANCES = No
    GEOM_NAME_FIELD = _geometry_name
    LIST_ATTR = list{}
    LIST_ATTR_MODE_LOOKUP = LEAN
    MODE = Flatten One Level
    PART_NUMBER_FIELD = _part_number
    SPLIT_COMPOSITES = No
    DEAGGREGATED -> PythonCaller_5

Bookmark: Colorize
PythonCaller_5
    NEW_ATTRIBUTES = fme_fill_color fme_color
    PYTHONSOURCE:
      import fmeobjects, math, colorsys
      # Template Function interface:
      def processFeature(feature):
         pass

      # Template Class Interface:
      class FeatureProcessor(object):
         def __init__(self):
             pass
         def input(self,feature):

             # Get the list of Unique Values
             rval=feature.getAttribute("rval")

             # Number of groups = number of Unique values
             bands=len(rval.split());

             # Get color scheme and attribute to color on, also initialize variables
             Value=float(feature.getAttribute("GC_Value"))
             cs=int(feature.getAttribute("GC_Color_Scheme"))
             R=0.0
             G=0.0
             B=0.0
             global bin
             i=0

             # for each value in the input list of unique values
             for val in rval.split():

                 # Check if the attribute value is equal to the break value used in this iteration
                 if Value==float(val):
                     [R,G,B]=self.color(i,cs,bands)
                     break

                 # if we have reached here, the attribute value has not been equal to the current unique value
                 # It does not belong to group i, so it might belong to group i+1
                 i=i+1

             # Set the feature's color
             feature.setAttribute("fme_color",str(R)+","+str(G)+","+str(B))
             feature.setAttribute("fme_fill_color",str(R)+","+str(G)+","+str(B))


             self.pyoutput(feature)
         def close(self):
             pass

         # This function sets feature's color based on the group it belongs to, the number of groups, and color scheme
         def color(self,i,cs,bands):
                     if (bands!=1):
                          bands-=1
                     if cs==1:
                          [R,G,B]=colorsys.hsv_to_rgb(float(i)/bands,1,1)
                     elif cs==2:
                          [R,G,B]=colorsys.hsv_to_rgb(1-float(i)/bands,1,1)
                     elif cs==3:
                          [R,G,B]=[1,float(i)/bands,float(i)/bands]
                     elif cs==4:
                          [R,G,B]=[1,1-float(i)/bands,1-float(i)/bands]
                     elif cs==5:
                          [R,G,B]=[float(i)/bands,float(i)/bands,1]
                     elif cs==6:
                          [R,G,B]=[1-float(i)/bands,1-float(i)/bands,1]
                     elif cs==7:
                          [R,G,B]=colorsys.hsv_to_rgb(float(i)/bands/3,1,1)
                     elif cs==8:
                          [R,G,B]=colorsys.hsv_to_rgb(1.0/3-float(i)/bands/3,1,1)
                     else:
                         [R,G,B]=[0,0,0]
                     return [R,G,B]
    PYTHONSYMBOL = FeatureProcessor
    -> AttributeRemover
